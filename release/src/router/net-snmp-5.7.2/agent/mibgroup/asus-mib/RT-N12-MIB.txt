RT-N12-MIB DEFINITIONS ::= BEGIN
	IMPORTS MODULE-IDENTITY, OBJECT-TYPE, 
		NOTIFICATION-TYPE,Integer32, Counter32  FROM SNMPv2-SMI 
		DisplayString , MacAddress, RowStatus,
		TruthValue                              FROM SNMPv2-TC
		private, IpAddress, TimeTicks		FROM RFC1155-SMI;
-- **********************************************************************
-- *  Tree Definition
-- **********************************************************************		
	enterprises		OBJECT IDENTIFIER ::= { private 1 }
	asus			OBJECT IDENTIFIER ::= { enterprises 2623 }
	asus-wireless		OBJECT IDENTIFIER ::= { asus 4 }
	rtn12			OBJECT IDENTIFIER ::= { asus-wireless 1 }
	rtn12Config		OBJECT IDENTIFIER ::= { rtn12 1 }
-- **********************************************************************
-- *  MODULE IDENTITY
-- **********************************************************************
--		rtn12Config MODULE-IDENTITY
--		LAST-UPDATED "201212271600Z"
--		ORGANIZATION "AsusTek"
--		CONTACT-INFO " "
--		DESCRIPTION
--	        "The MIB module for Asus RT-N12."
--		::= { rtn12 1 }	
-- **********************************************************************
-- *  Major sections
-- **********************************************************************
	wireless		OBJECT IDENTIFIER ::= { rtn12Config 1 }	
	lan			OBJECT IDENTIFIER ::= { rtn12Config 2 }
	wan			OBJECT IDENTIFIER ::= { rtn12Config 3 }
	ipv6			OBJECT IDENTIFIER ::= { rtn12Config 4 }
	vpn-server		OBJECT IDENTIFIER ::= { rtn12Config 5 }
	firewall		OBJECT IDENTIFIER ::= { rtn12Config 6 }
	administration		OBJECT IDENTIFIER ::= { rtn12Config 7 }
	system-log		OBJECT IDENTIFIER ::= { rtn12Config 8 }
	guest-network		OBJECT IDENTIFIER ::= { rtn12Config 9 }
	traffic-manager		OBJECT IDENTIFIER ::= { rtn12Config 10 }
	quick-internet-setup	OBJECT IDENTIFIER ::= { rtn12Config 11 }

-- **********************************************************************
-- *  MIB attribute OBJECT-TYPE definitions follow
-- **********************************************************************

-- ======================================================================
-- * Wireless Section
-- ======================================================================
-- **********************************************************************
-- *  2.4G Section
-- **********************************************************************

	wl2g			OBJECT IDENTIFIER ::= { wireless 1 }

-- ++++++++++++++++++++++++++++++++++++++++++++++++++++++++++++++++++++++
-- +  General Section (2.4G)
-- ++++++++++++++++++++++++++++++++++++++++++++++++++++++++++++++++++++++

	generalWl2g		OBJECT IDENTIFIER ::= { wl2g 1 }

	ssidWl2g		OBJECT-TYPE
                                SYNTAX OCTET STRING ( SIZE (1..32) )
                                MAX-ACCESS read-write
                                STATUS current
                                DESCRIPTION
					"The network name or SSID is a unique name that identifies the wireless 
					network. WiFi devices automatically detect all networks within range. 
					Assign an identification string of up to 32 characters for your wireless 
					connection."
                                ::= { generalWl2g 1 }

	hideSSIDWl2g		OBJECT-TYPE
                                SYNTAX INTEGER { yes(1), no(2) }
				MAX-ACCESS read-write
                                STATUS current
				DESCRIPTION
		                        "If [YES] is selected, your SSID does not show in site surveys by wireless 
					mobile clients and they can only connect to your ASUS Wireless Router with 
					your SSID of AP."
				::= { generalWl2g 2 }

	wirelessModeWl2g	OBJECT-TYPE
                                SYNTAX INTEGER { auto(1), dot11N-only(2), legacy(3) }
				MAX-ACCESS read-write
				STATUS current
				DESCRIPTION
					"This item allows you to select any of these options for the Wireless Mode 
					of your 802.11n interface. [Auto]: Allows 802.11n, 802.11g, and 802.11b 
					devices to connect to RT-N12. [Legacy]: Allows 802.11b/g/n devices to 
					connect to RT-N12, but 802.11n devices only run at a speed of 54Mbps. 
					[n Only]: Maximizes performance, but does not allow 802.11g and 802.11b 
					devices to connect to your device."
				::= { generalWl2g 3 }

	protectionWl2g		OBJECT-TYPE
                                SYNTAX INTEGER { enable(1), disable(2) }
				MAX-ACCESS read-write
				STATUS current                                                        
                                DESCRIPTION
					"Tick b/g Protection to allow b/g devices to connect to RT-N12 without 
					affecting 11n devices, but this increases the router's workload."
                                ::= { generalWl2g 4 }

	channelBandwidthWl2g	OBJECT-TYPE
                                SYNTAX INTEGER { 20MHz(1), 20-or-40MHz(2), 40MHz(3) }
				MAX-ACCESS read-write
				STATUS current                                                        
                                DESCRIPTION
					"Selecting a wider channel bandwidth provides you with a higher transmission 
					speed. Uses 40MHz coexistent bandwidth to maximize the wireless throughput. 
					If you experience issues with wireless stability, please choose the default 
					mode (20MHz)."
                                ::= { generalWl2g 5 }

	controlChannelWl2g	OBJECT-TYPE
                                SYNTAX INTEGER
                                MAX-ACCESS read-write
                                STATUS current
                                DESCRIPTION
		                        "The radio channel for wireless connection operation."
                                ::= { generalWl2g 6 }

	extensionChannelWl2g	OBJECT-TYPE
                                SYNTAX INTEGER { auto(1), lower(2), upper(3) }
                                MAX-ACCESS read-write
                                STATUS current
                                DESCRIPTION
		                        "Select the extension channel used in the 20/40MHz channel bandwidth mode. 
					802.11n uses the extension channel to get extra speed. For channels 1 to 4, 
					you can only select an upper channel. For channels 5 to 7, you can select a 
					lower or an upper channel as the extension channel. For channels above 7, 
					you can only select a lower channel."
				::= { generalWl2g 7 }

	authenticationWl2g	OBJECT-TYPE                              
                                SYNTAX INTEGER { open-system(1), shared-key(2), wpa-personal(3), wpa2-personal(4), wpa-auto-personal(5), wpa-enterprise(6), wpa2-enterprise(7), wpa-auto-enterprise(8), radius-with-8021x(9) }
				MAX-ACCESS read-write
				STATUS current
				DESCRIPTION
					"This field enables the authentication methods for wireless clients."
				::= { generalWl2g 8 }

	wepEncryptionWl2g	OBJECT-TYPE
				SYNTAX INTEGER { none(1), wep-64bits(2), wep-128bits(3) }
				MAX-ACCESS read-write
				STATUS current
				DESCRIPTION 
					"Enable WEP Encyption to encrypt data."
				::= { generalWl2g 9 }

	keyIndexWl2g		OBJECT-TYPE
				SYNTAX INTEGER { first(1), second(2), third(3), forth(4) }
				MAX-ACCESS read-write                      
                                STATUS current
				DESCRIPTION
					"Default transmit WEP Key."
				::= { generalWl2g 10 }       
                                
	wl2gWepKeyTable		OBJECT-TYPE
				SYNTAX SEQUENCE OF WepKeyEntryWl2g
				MAX-ACCESS not-accessible
                                STATUS current
                                DESCRIPTION
                                	"Wep Key Table."
                                ::= { generalWl2g 11 }

	wepKeyEntryWl2g		OBJECT-TYPE
                                SYNTAX WepKeyEntryWl2g
                                MAX-ACCESS not-accessible
                                STATUS current
                                DESCRIPTION ""
                                INDEX { wepKeyIndexWl2g }
                                ::= { wl2gWepKeyTable 1 }

 	WepKeyEntryWl2g ::= SEQUENCE {
        	wepKeyIndexWl2g		INTEGER,
        	wepKeyValueWl2g		OCTET STRING
    	}                                    

	wepKeyIndexWl2g		OBJECT-TYPE
                                SYNTAX INTEGER ( 1..4 )
                                MAX-ACCESS not-accessible
                                STATUS current
                                DESCRIPTION
                                	"Wep key index."
                                ::= { wepKeyEntryWl2g 1 }

	wepKeyValueWl2g		OBJECT-TYPE
                                SYNTAX OCTET STRING
                                MAX-ACCESS read-write
                                STATUS current
                                DESCRIPTION
                                	"WEP key value."
                                ::= { wepKeyEntryWl2g  2 } 

	passphraseWl2g		OBJECT-TYPE
                                SYNTAX OCTET STRING
                                MAX-ACCESS read-write
                                STATUS current
				DESCRIPTION
					"If you select WEP Encryption, you can key in some words in this field to 
					generate WEP keys automatically."
				::= { generalWl2g 12 } 
                                
	wpaEncryptionWl2g	OBJECT-TYPE
				SYNTAX INTEGER { tkip(1), aes(2), tkip-aes(3) }
				MAX-ACCESS read-write
				STATUS current
				DESCRIPTION
					"Enable WPA Encryption to encrypt data."   
                                ::= { generalWl2g 13 }

	wpaPreSharedKeyWl2g	OBJECT-TYPE
                                SYNTAX OCTET STRING
                                MAX-ACCESS read-write
                                STATUS current
				DESCRIPTION
					"This field requires a password of 8 and 63 characters(letters, numbers or 
					a combination) or 64 hex digits to start the encryption process ."
				::= { generalWl2g 14 }

	keyRotationIntervalWl2g	OBJECT-TYPE
				SYNTAX INTEGER
				MAX-ACCESS read-write
				STATUS current
				DESCRIPTION
					"This field specifies the interval (in seconds) after which a WPA group key 
					is changed . Enter [0] (zero) to indicate that a periodic key-change is not 
					required."
				::= { generalWl2g 15 }

-- ++++++++++++++++++++++++++++++++++++++++++++++++++++++++++++++++++++++
-- *  End of General Section (2.4G)
-- ++++++++++++++++++++++++++++++++++++++++++++++++++++++++++++++++++++++

-- ++++++++++++++++++++++++++++++++++++++++++++++++++++++++++++++++++++++
-- +  WPS Section (2.4G)
-- ++++++++++++++++++++++++++++++++++++++++++++++++++++++++++++++++++++++

	wpsWl2g			OBJECT IDENTIFIER ::= { wl2g 2 }

	enableWPSWl2g		OBJECT-TYPE
                                SYNTAX INTEGER { enable(1), disable(2) }
				MAX-ACCESS read-write
				STATUS current                                                        
                                DESCRIPTION
					"Selecting Yes allows Wi-Fi Protected Setup (WPS) to simplify the process of 
					connecting any device to the wireless network. WPS support the authentication 
					of Open system, WPA-Personal, WPA2-Personal. Not support Shared Key, 
					WPA-Enterprise, WPA2-Enterprise and Radius."
				::= { wpsWl2g 1 }

	connectionStatusWl2g	OBJECT-TYPE
                                SYNTAX OCTET STRING
                                MAX-ACCESS read-only
                                STATUS current
                                DESCRIPTION ""
                                ::= { wpsWl2g 2 }

	configuredWl2g		OBJECT-TYPE
                                SYNTAX OCTET STRING
                                MAX-ACCESS read-only
                                STATUS current
                                DESCRIPTION ""
                                ::= { wpsWl2g 3 }

	apPinCodeWl2g		OBJECT-TYPE
                                SYNTAX OCTET STRING
                                MAX-ACCESS read-only
                                STATUS current
                                DESCRIPTION
					"Key in the router's PIN code in the client's WPS utility and configure the 
					network name and security settings."
                                ::= { wpsWl2g 4 }

	clientPinCodeWl2g	OBJECT-TYPE
                                SYNTAX OCTET STRING
				MAX-ACCESS read-write
                                STATUS current
                                DESCRIPTION ""
                                ::= { wpsWl2g 5 }

-- ++++++++++++++++++++++++++++++++++++++++++++++++++++++++++++++++++++++
-- *  End of WPS Section (2.4G)
-- ++++++++++++++++++++++++++++++++++++++++++++++++++++++++++++++++++++++

-- ++++++++++++++++++++++++++++++++++++++++++++++++++++++++++++++++++++++
-- +  Bridge Section (2.4G)
-- ++++++++++++++++++++++++++++++++++++++++++++++++++++++++++++++++++++++

	bridgeWl2g		OBJECT IDENTIFIER ::= { wl2g 3 }

	wbApModeWl2g		OBJECT-TYPE
                               	SYNTAX INTEGER { ap-only(1), wds-only(2), hybrid(3) }
				MAX-ACCESS read-write
				STATUS current
				DESCRIPTION
					"Select [AP Only] to disable Wireless Bridge function. Select [WDS Only] to 
					disable local wireless station connection. Select [Hybrid] to enable Wireless 
					bridge function and wireless stations will be able to connect to the AP."
				::= { bridgeWl2g 1 }

	wbConnectRemoteBridegeAPWl2g	OBJECT-TYPE
				SYNTAX INTEGER { yes(1), no(2) }
				MAX-ACCESS read-write
				STATUS current
				DESCRIPTION
					"Select [Yes] to connect RT-N12 to other APs listed in the Remote AP List."
				::= { bridgeWl2g 2 }

	wbChannelWl2g		OBJECT-TYPE
				SYNTAX INTEGER
				MAX-ACCESS read-write
				STATUS current
				DESCRIPTION
					"The radio channel for wireless connection operation."
				::= { bridgeWl2g 3 }

	wbRemoteBridgeScanWl2g	OBJECT IDENTIFIER ::= { bridgeWl2g 4 }

	wbBridgeAPScanActWl2g	OBJECT-TYPE
				SYNTAX INTEGER { scan(1), nothing(2) }
				MAX-ACCESS read-write
				STATUS current
				DESCRIPTION ""
				::= { wbRemoteBridgeScanWl2g 1 }

	wbWl2gBridgeAPScanTable	OBJECT-TYPE
				SYNTAX SEQUENCE OF WbBridgeAPScanEntryWl2g
				MAX-ACCESS not-accessible
				STATUS current
				DESCRIPTION ""
                                ::= { wbRemoteBridgeScanWl2g 2 }

	wbBridgeAPScanEntryWl2g	OBJECT-TYPE
				SYNTAX WbBridgeAPScanEntryWl2g
				MAX-ACCESS not-accessible
				STATUS current
				DESCRIPTION ""
				INDEX { wbAPResultIndexWl2g }
				::= { wbWl2gBridgeAPScanTable 1 }

 	WbBridgeAPScanEntryWl2g ::= SEQUENCE {
        	wbAPResultIndexWl2g    		INTEGER,
        	wbAPResultBSSIDWl2g	        OCTET STRING,
        	wbAPResultSSIDWl2g		OCTET STRING
    	}

	wbAPResultIndexWl2g	OBJECT-TYPE
				SYNTAX INTEGER ( 1..32 )
				MAX-ACCESS not-accessible
				STATUS current
				DESCRIPTION
					"AP scan result entry index."
				::= { wbBridgeAPScanEntryWl2g 1 }

	wbAPResultBSSIDWl2g	OBJECT-TYPE
				SYNTAX OCTET STRING
				MAX-ACCESS read-only
				STATUS current
				DESCRIPTION
					"BSSID of the AP scan result."
				::= { wbBridgeAPScanEntryWl2g  2 }

	wbAPResultSSIDWl2g	OBJECT-TYPE
				SYNTAX OCTET STRING ( SIZE (1..32) )
				MAX-ACCESS read-only
				STATUS current
				DESCRIPTION
					"SSID of the AP scan result."
				::= { wbBridgeAPScanEntryWl2g 3 }

	wbWl2gRemoteAPTable	OBJECT-TYPE
				SYNTAX SEQUENCE OF WBRemoteAPEntryWl2g
				MAX-ACCESS not-accessible
				STATUS current
				DESCRIPTION
					"Remote AP list."
				::= { bridgeWl2g 5 }

	wbRemoteAPEntryWl2g	OBJECT-TYPE
				SYNTAX WBRemoteAPEntryWl2g
				MAX-ACCESS not-accessible
				STATUS current
				DESCRIPTION ""
				INDEX { wbRemoteAPIndexWl2g }
				::= { wbWl2gRemoteAPTable 1 }

 	WBRemoteAPEntryWl2g ::= SEQUENCE {
        	wbRemoteAPIndexWl2g	INTEGER,
        	wbRemoteAPMACAddrWl2g	MacAddress,
        	wbRemoteAPDelEntryWl2g	INTEGER
    	}                           
    
	wbRemoteAPIndexWl2g	OBJECT-TYPE
				SYNTAX INTEGER ( 1..4 )
				MAX-ACCESS not-accessible
				STATUS current
				DESCRIPTION 
					"Remote AP Index."
				::= { wbRemoteAPEntryWl2g 1 }

	wbRemoteAPMACAddrWl2g	OBJECT-TYPE
				SYNTAX MacAddress
				MAX-ACCESS read-write
				STATUS current
				DESCRIPTION
					"MAC address of remote bridge APs."
				::= { wbRemoteAPEntryWl2g  2 } 

	wbRemoteAPDelEntryWl2g	OBJECT-TYPE
				SYNTAX INTEGER { yes(1), no(2) }
				MAX-ACCESS read-write
				STATUS current
				DESCRIPTION
					"Delete the AP enntry."
				::= { wbRemoteAPEntryWl2g 3 }

-- ++++++++++++++++++++++++++++++++++++++++++++++++++++++++++++++++++++++
-- *  End of Bridge Section (2.4G)
-- ++++++++++++++++++++++++++++++++++++++++++++++++++++++++++++++++++++++

-- ++++++++++++++++++++++++++++++++++++++++++++++++++++++++++++++++++++++
-- +  Mac Filter Section (2.4G)
-- ++++++++++++++++++++++++++++++++++++++++++++++++++++++++++++++++++++++

	macFilterWl2g		OBJECT IDENTIFIER ::= { wl2g 4 }

	macFilterModeWl2g	OBJECT-TYPE
				SYNTAX INTEGER { disable(1), accept(2), reject(3) }
				MAX-ACCESS read-write
				STATUS current
				DESCRIPTION
					"In Accept mode, RT-N12 only accept clients with MAC address in the list. In 
					Reject mode, RT-N12 will reject clients with MAC address in the list."
				::= { macFilterWl2g 1 }

	wl2gMacFilterTable	OBJECT-TYPE
				SYNTAX SEQUENCE OF MacFilterEntryWl2g
				MAX-ACCESS not-accessible
				STATUS current
				DESCRIPTION
					"Mac filter list."
                                ::= { macFilterWl2g 2 }
                                    
	macFilterEntryWl2g	OBJECT-TYPE
				SYNTAX MacFilterEntryWl2g
                                MAX-ACCESS not-accessible
				STATUS current
				DESCRIPTION ""
				INDEX { macFilterIndexWl2g }
				::= { wl2gMacFilterTable 1 }

 	MacFilterEntryWl2g ::= SEQUENCE {
        	macFilterIndexWl2g	INTEGER,
        	macFilterMACAddrWl2g	MacAddress,
        	macFilterDelEntryWl2g	INTEGER
    	}                           
    
	macFilterIndexWl2g	OBJECT-TYPE
				SYNTAX INTEGER ( 1..64 )
				MAX-ACCESS not-accessible
				STATUS current
				DESCRIPTION
					"Mac filter list index"
				::= { macFilterEntryWl2g 1 }

	macFilterMACAddrWl2g	OBJECT-TYPE
				SYNTAX MacAddress
				MAX-ACCESS read-write
				STATUS current
				DESCRIPTION
					"MAC address of station which device controls its access."
				::= { macFilterEntryWl2g  2 } 
	
	macFilterDelEntryWl2g	OBJECT-TYPE
				SYNTAX INTEGER { yes(1), no(2) }
				MAX-ACCESS read-write
				STATUS current
				DESCRIPTION
					"Delete the mac filter entry."
				::= { macFilterEntryWl2g 3 }

-- ++++++++++++++++++++++++++++++++++++++++++++++++++++++++++++++++++++++
-- *  End of Mac Filter Section (2.4G)
-- ++++++++++++++++++++++++++++++++++++++++++++++++++++++++++++++++++++++

-- ++++++++++++++++++++++++++++++++++++++++++++++++++++++++++++++++++++++
-- +  Radius Setting Section (2.4G)
-- ++++++++++++++++++++++++++++++++++++++++++++++++++++++++++++++++++++++

	radiusSettingWl2g	OBJECT IDENTIFIER ::= { wl2g 5 }

	radiusServerIPAddrWl2g	OBJECT-TYPE
				SYNTAX OCTET STRING ( SIZE (0..39) )
				MAX-ACCESS read-write
				STATUS current
				DESCRIPTION
					"The IP address of the RADIUS server for wireless authentication and dynamic WEP 
					key derivation."
				::= { radiusSettingWl2g 1 }

	radiusPortWl2g		OBJECT-TYPE
				SYNTAX INTEGER (0..65535)
				MAX-ACCESS read-write
				STATUS current
				DESCRIPTION
					"The UDP port number for connection to the RADIUS server."
                                ::= { radiusSettingWl2g 2 }

	radiusConnectionSecretWl2g	OBJECT-TYPE
				SYNTAX OCTET STRING
				MAX-ACCESS read-write
				STATUS current
				DESCRIPTION
					"The password to connect to the RADIUS server."
				::= { radiusSettingWl2g 3 }

-- ++++++++++++++++++++++++++++++++++++++++++++++++++++++++++++++++++++++
-- *  End of Radius Setting Section (2.4G)
-- ++++++++++++++++++++++++++++++++++++++++++++++++++++++++++++++++++++++

-- ++++++++++++++++++++++++++++++++++++++++++++++++++++++++++++++++++++++
-- +  Professional Section (2.4G)
-- ++++++++++++++++++++++++++++++++++++++++++++++++++++++++++++++++++++++

	professionalWl2g	OBJECT IDENTIFIER ::= { wl2g 6 }

	radioWl2g		OBJECT-TYPE
				SYNTAX INTEGER { yes(1), no(2) }
				MAX-ACCESS read-write
				STATUS current
				DESCRIPTION
					"Select [Yes] to enable radio function."                                           
                                ::= { professionalWl2g 1 }

	weekDaysEnableRadioWl2g	OBJECT-TYPE
				SYNTAX BITS { monday(0), tuesday(1), wednesday(2), thursday(3), friday(4) }
				MAX-ACCESS read-write
				STATUS current
				DESCRIPTION
					"This field defines the dates that wireless function is enabled."
				::= { professionalWl2g 2 }

	weekDaysRadioStartTimeHWl2g	OBJECT-TYPE
				SYNTAX INTEGER ( 0..23 )              
                                MAX-ACCESS read-write
				STATUS current
				DESCRIPTION
					"Hour of starting time of weekdays to enable 2.4G radio."
				::= { professionalWl2g 3 }

	weekDaysRadioStartTimeMWl2g	OBJECT-TYPE
				SYNTAX INTEGER ( 0..59 )
				MAX-ACCESS read-write
				STATUS current
				DESCRIPTION
					"Minute of starting time of weekdays to enable 2.4G radio."
				::= { professionalWl2g 4 }

	weekDaysRadioEndTimeHWl2g	OBJECT-TYPE
				SYNTAX INTEGER ( 0..23 )              
                                MAX-ACCESS read-write
				STATUS current
				DESCRIPTION
					"Hour of ending time of weekdays to enable 2.4G radio."
				::= { professionalWl2g 5 }

	weekDaysRadioEndTimeMWl2g	OBJECT-TYPE
				SYNTAX INTEGER ( 0..59 )
				MAX-ACCESS read-write
				STATUS current
				DESCRIPTION
					"Minute of ending time of weekdays to enable 2.4G radio."
				::= { professionalWl2g 6 }

	weekendEnableRadioWl2g	OBJECT-TYPE
				SYNTAX BITS { saturday(0), sunday(1) }
				MAX-ACCESS read-write
				STATUS current
				DESCRIPTION
					"This field defines the dates that wireless function is enabled."
				::= { professionalWl2g 7 }

	weekendRadioStartTimeHWl2g	OBJECT-TYPE
				SYNTAX INTEGER ( 0..23 )              
                                MAX-ACCESS read-write
				STATUS current
				DESCRIPTION
					"Hour of starting time of weekend to enable 2.4G radio."
				::= { professionalWl2g 8 }

	weekendRadioStartTimeMWl2g	OBJECT-TYPE
				SYNTAX INTEGER ( 0..59 )
				MAX-ACCESS read-write
				STATUS current
				DESCRIPTION
					"Minute of starting time of weekend to enable 2.4G radio."
				::= { professionalWl2g 9 }

	weekendRadioEndTimeHWl2g	OBJECT-TYPE
				SYNTAX INTEGER ( 0..23 )              
                                MAX-ACCESS read-write
				STATUS current
				DESCRIPTION
					"Hour of ending time of weekend to enable 2.4G radio."
				::= { professionalWl2g 10 }

	weekendRadioEndTimeMWl2g	OBJECT-TYPE
				SYNTAX INTEGER ( 0..59 )
				MAX-ACCESS read-write
				STATUS current
				DESCRIPTION
					"Minute of ending time of weekend to enable 2.4G radio."
				::= { professionalWl2g 11 }

	apIsolatedWl2g		OBJECT-TYPE
				SYNTAX INTEGER { yes(1), no(2) }
				MAX-ACCESS read-write
				STATUS current
				DESCRIPTION
					"When this feature is enabled, wireless clients or devices will not be able 
					to communicate with each other. You may want to utilize this feature if you 
					have many guests that frequent your wireless network."
				::= { professionalWl2g 12 }

	multicastRateWl2g	OBJECT-TYPE
				SYNTAX INTEGER { disable(1), OFDM-6(2), OFDM-9(3), OFDM-12(4), OFDM-18(5), OFDM-24(6), OFDM-36(7), OFDM-48(8), OFDM-54(9), CCK-1(10), CCK-2(11), CCK-5(12), CCK-11(13) }
				MAX-ACCESS read-write
				STATUS current
				DESCRIPTION
					"Select the multicast transmission rate. You are recommended to select Auto to 
					maximize performance."
				::= { professionalWl2g 13 }

	preambleTypeWl2g	OBJECT-TYPE
				SYNTAX INTEGER { long(1), short(2), auto(3) }
				MAX-ACCESS read-write
				STATUS current
				DESCRIPTION
					"The Preamble type defines the length of the CRC (Cyclic Redundancy Check) 
					block, which is a technique for detecting data transmission errors among 
					wireless devices. We recommend that you configure all wireless devices to the 
					same preamble type. Use short preamble for wireless devices in high network 
					traffic areas. Use long preamble for older wireless devices."
				::= { professionalWl2g 14 }

	fragmentationThresholdWl2g	OBJECT-TYPE
				SYNTAX INTEGER (256..2346)
				MAX-ACCESS read-write
				STATUS current
				DESCRIPTION
					"Fragmentation Threshold sets the frame size of incoming messages (ranging from 256 
					to 2346 bytes) used as fragmentation boundary. If the frame size is too big, the 
					heavy interference affects transmission reliability. If the frame size is too small, 
					it decreases transmission efficiency."
				::= { professionalWl2g 15 }

	rtsThresholdWl2g	OBJECT-TYPE
				SYNTAX INTEGER (0..2347)
				MAX-ACCESS read-write
				STATUS current
				DESCRIPTION
					"Lower the signal RTS (Request To Send) to promote the transmission efficiency 
					in condition of noisy environment or too many clients."
				::= { professionalWl2g 16 }

	dtimIntervalWl2g	OBJECT-TYPE
				SYNTAX INTEGER (1..255)
				MAX-ACCESS read-write
				STATUS current
				DESCRIPTION
					"DTIM (Delivery Traffic Indication Message) is included in Beacon packet.The 
					DTIM Interval (1-255) means the period of time to wake up wireless clients from 
					Sleep Mode. The default value is 3."
				::= { professionalWl2g 17 }

	beaconIntervalWl2g	OBJECT-TYPE
				SYNTAX INTEGER (20..1000)
				MAX-ACCESS read-write
				STATUS current
				DESCRIPTION
					"Beacon Interval means the period of time between one beacon and the next one. 
					The default value is 100 (the unit is millisecond, or 1/1000 second). Lower the 
					Beacon Interval to improve transmission performance in unstable environment or for 
					roaming clients, but it will be power consuming."
				::= { professionalWl2g 18 }

	txBurstingWl2g		OBJECT-TYPE
				SYNTAX INTEGER { enable(1), disable(2) }
				MAX-ACCESS read-write
				STATUS current
				DESCRIPTION
					"Selecting [Enable] enables TX Bursting to improve the transmission speed (from AP 
					to client) of g devices."
				::= { professionalWl2g 19 }

--	wmmWl2g			OBJECT-TYPE
--				SYNTAX INTEGER { auto(1), enable(2), disable(3) }
--				MAX-ACCESS read-write
--				STATUS current
--				DESCRIPTION
--					"Enable WMM (Wi-Fi Multimedia) to improve user experience of multimedia applications 
--					on your wireless network."
--				::= { professionalWl2g 20 }

--	wmmNoAcknowledgementWl2g			OBJECT-TYPE
--				SYNTAX INTEGER { enable(1), disable(2) }
--				MAX-ACCESS read-write
--				STATUS current
--				DESCRIPTION
--					"[No-Acknowledgement] is the acknowledge policy at MAC level. When enabled, it results 
--					in more efficient throughput but higher error rates in a noisy Radio Frequency (RF) 
--					environment."
--				::= { professionalWl2g 21 }

	multicastForwardingWl2g	OBJECT-TYPE
				SYNTAX INTEGER { enable(1), disable(2) }
				MAX-ACCESS read-write
				STATUS current
				DESCRIPTION ""
				::= { professionalWl2g 22 }

	wmmAPSDWl2g		OBJECT-TYPE
				SYNTAX INTEGER { enable(1), disable(2) }
				MAX-ACCESS read-write
				STATUS current
				DESCRIPTION
					"Enable or Disable WMM APSD (Automatic Power Save Delivery)."
				::= { professionalWl2g 23 }

	interferenceManagementWl2g		OBJECT-TYPE
				SYNTAX INTEGER { enable(1), disable(2) }
				MAX-ACCESS read-write
				STATUS current
				DESCRIPTION
					"When this option is enabled, router performance will improve in an environment where 
					there is high interference, but it might reduce connection stability under some circumstances."
				::= { professionalWl2g 24 }

--	txPowerAdjustmentWl2g	OBJECT-TYPE
--				SYNTAX INTEGER (0..100)
--				MAX-ACCESS read-write
--				STATUS current
--				DESCRIPTION
--					"Increase Tx Power to enhance the transmission quality or decrease Tx Power to reduce 
--					power consumption."
--				::= { professionalWl2g 25 }

-- ++++++++++++++++++++++++++++++++++++++++++++++++++++++++++++++++++++++
-- *  End of Professional Section (2.4G)
-- ++++++++++++++++++++++++++++++++++++++++++++++++++++++++++++++++++++++

-- **********************************************************************
-- *  End of 2.4G Section
-- **********************************************************************

-- ======================================================================
-- * End of Wireless Section
-- ======================================================================




-- ======================================================================
-- * LAN Section
-- ======================================================================

-- **********************************************************************
-- *  LAN IP Config Section 
-- **********************************************************************

	lan-ip			OBJECT IDENTIFIER ::= { lan 1 }

	lGetIpAutomatically	OBJECT-TYPE
				SYNTAX INTEGER { yes(1), no(2) }
				MAX-ACCESS read-write
				STATUS current
				DESCRIPTION ""
                                ::= { lan-ip 1 }
	
	lIPAddress		OBJECT-TYPE
				SYNTAX IpAddress
				MAX-ACCESS read-write
				STATUS current
				DESCRIPTION
		                        "The value of this object is IP Address of the device as seen in your local network. 
					The default value is 192.168.1.1."
                                ::= { lan-ip 2 }

	lSubnetMask		OBJECT-TYPE
				SYNTAX IpAddress
				MAX-ACCESS read-write
				STATUS current
				DESCRIPTION
					"The value this object is Subnet Mask of the device as seen in your local network. 
					The default value is 255.255.255.0."
				::= { lan-ip 3 }

	lDefaultGateway		OBJECT-TYPE
				SYNTAX IpAddress
				MAX-ACCESS read-write
				STATUS current
				DESCRIPTION ""
				::= { lan-ip 4 }

	lConnectToDnsServerAutomatically	OBJECT-TYPE
				SYNTAX INTEGER { yes(1), no(2) }
				MAX-ACCESS read-write
				STATUS current
				DESCRIPTION ""
                                ::= { lan-ip 5 }

	lDnsServer1		OBJECT-TYPE
				SYNTAX IpAddress
				MAX-ACCESS read-write
				STATUS current
				DESCRIPTION ""
				::= { lan-ip 6 }

	lDnsServer2		OBJECT-TYPE
				SYNTAX IpAddress
				MAX-ACCESS read-write
				STATUS current
				DESCRIPTION ""
				::= { lan-ip 7 }

-- **********************************************************************
-- *  End of LAN IP Config Section 
-- **********************************************************************

-- **********************************************************************
-- *  DHCP server Config Section 
-- **********************************************************************

	dhcp-server		OBJECT IDENTIFIER ::= { lan 2 }

	basic-config-ds		OBJECT IDENTIFIER ::= { dhcp-server 1 }

	enableDHCPServer	OBJECT-TYPE
                                SYNTAX INTEGER { yes(1), no(2) }
				MAX-ACCESS read-write
                                STATUS current
				DESCRIPTION
					"Enable the DHCP server function to allow the router's DHCP server to automatically assign 
					IP addresses to network clients. If this function is disabled, you need to manually assign 
					the IP address settings on your LAN devices."
				::= { basic-config-ds 1 }

	domainName		OBJECT-TYPE
                                SYNTAX OCTET STRING ( SIZE (1..32) )
                                MAX-ACCESS read-write
                                STATUS current
                                DESCRIPTION
					"The Domain Name for clients who request IP Address from the DHCP Server."
                                ::= { basic-config-ds 2 }

	ipPoolStartingAddress	OBJECT-TYPE
				SYNTAX IpAddress
				MAX-ACCESS read-write
				STATUS current
				DESCRIPTION
					"The first address in the pool to be assigned by the DHCP server in LAN."
				::= { basic-config-ds 3 }

	ipPoolEndingAddress	OBJECT-TYPE
				SYNTAX IpAddress
				MAX-ACCESS read-write
				STATUS current
				DESCRIPTION
					"This field indicates the last address in the pool to be assigned by the DHCP server in LAN."
				::= { basic-config-ds 4 }

	leaseTime		OBJECT-TYPE
				SYNTAX INTEGER
				MAX-ACCESS read-write
				STATUS current
				DESCRIPTION
					"Set the lease time that the network client is allowed to use its current IP address to 
					connect to the wireless router. When the lease time expires, the network client should 
					either renew or get a new IP address from the wireless router's DHCP server."
				::= { basic-config-ds 5 }

	defaultGateway		OBJECT-TYPE
				SYNTAX IpAddress
				MAX-ACCESS read-write
				STATUS current
				DESCRIPTION
					"This field indicates the IP address of gateway in your LAN. If you leave it blank, the 
					IP address of RT-N12 will be assigned."
				::= { basic-config-ds 6 }

	dns-wins-server		OBJECT IDENTIFIER ::= { dhcp-server 2 }

	dnsServer		OBJECT-TYPE
				SYNTAX IpAddress
				MAX-ACCESS read-write
				STATUS current
				DESCRIPTION
					"This field indicates the IP address of DNS to provide to clients that request IP Address 
					from DHCP Server. You can leave it blank, then the DNS request will be processed by RT-N12."
				::= { dns-wins-server 1 }

	winsServer		OBJECT-TYPE
				SYNTAX IpAddress
				MAX-ACCESS read-write
				STATUS current
				DESCRIPTION
					"The Windows Internet Naming Service manages interaction of each PC with the Internet. 
					If you use a WINS server, enter IP Address of server here."
				::= { dns-wins-server 2 }

	manual-assignment	OBJECT IDENTIFIER ::= { dhcp-server 3 }

	enableManualAssignment	OBJECT-TYPE
                                SYNTAX INTEGER { yes(1), no(2) }
				MAX-ACCESS read-write
                                STATUS current
				DESCRIPTION
					"Assign a fixed IP address for a specific client. The client's MAC address is required."
				::= { manual-assignment 1 }

	dsClientListAct		OBJECT-TYPE
				SYNTAX INTEGER { scan(1), nothing(2) }
				MAX-ACCESS read-write
				STATUS current
				DESCRIPTION ""
				::= { manual-assignment 2 }

	dsClientTable		OBJECT-TYPE
				SYNTAX SEQUENCE OF DsClientEntry
				MAX-ACCESS not-accessible
				STATUS current
				DESCRIPTION ""
                                ::= { manual-assignment 3 }

	dsClientEntry		OBJECT-TYPE
				SYNTAX DsClientEntry
				MAX-ACCESS not-accessible
				STATUS current
				DESCRIPTION ""
				INDEX { dsClientIndex }
				::= { dsClientTable 1 }

 	DsClientEntry ::= SEQUENCE {
        	dsClientIndex    	INTEGER,
        	dsClientMACAddr	        OCTET STRING,
		dsClientIPAddr	        IpAddress,
        	dsClientName		OCTET STRING
    	}

	dsClientIndex		OBJECT-TYPE
				SYNTAX INTEGER ( 1..32 )
				MAX-ACCESS not-accessible
				STATUS current
				DESCRIPTION
					"Client entry index."
				::= { dsClientEntry 1 }

	dsClientMACAddr		OBJECT-TYPE
				SYNTAX OCTET STRING
				MAX-ACCESS read-only
				STATUS current
				DESCRIPTION
					"MAC address of the client list."
				::= { dsClientEntry 2 }

	dsClientIPAddr		OBJECT-TYPE
				SYNTAX IpAddress
				MAX-ACCESS read-only
				STATUS current
				DESCRIPTION
					"IP address of the client list."
				::= { dsClientEntry 3 }

	dsClientName		OBJECT-TYPE
				SYNTAX OCTET STRING
				MAX-ACCESS read-only
				STATUS current
				DESCRIPTION
					"Name of the client list."
				::= { dsClientEntry 4 }

	assignedIPTable		OBJECT-TYPE
				SYNTAX SEQUENCE OF AssignedIPEntry
				MAX-ACCESS not-accessible
				STATUS current
				DESCRIPTION
					"Assigned IP around the DHCP list."
				::= { manual-assignment 4 }

	assignedIPEntry		OBJECT-TYPE
				SYNTAX AssignedIPEntry
				MAX-ACCESS not-accessible
				STATUS current
				DESCRIPTION ""
				INDEX { assignedIPIndex }
				::= { assignedIPTable 1 }

 	AssignedIPEntry ::= SEQUENCE {
        	assignedIPIndex		INTEGER,
        	assignedIPMACAddr	MacAddress,
		assignedIPIPAddr	IpAddress,
        	assignedIPDelEntry	INTEGER
    	}                           
    
	assignedIPIndex	OBJECT-TYPE
				SYNTAX INTEGER
				MAX-ACCESS not-accessible
				STATUS current
				DESCRIPTION 
					"Remote AP Index."
				::= { assignedIPEntry 1 }

	assignedIPMACAddr	OBJECT-TYPE
				SYNTAX MacAddress
				MAX-ACCESS read-write
				STATUS current
				DESCRIPTION
					"MAC address of assigned IP around the DHCP list."
				::= { assignedIPEntry  2 }

	assignedIPIPAddr	OBJECT-TYPE
				SYNTAX IpAddress
				MAX-ACCESS read-write
				STATUS current
				DESCRIPTION
					"IP address of assigned IP around the DHCP list."
				::= { assignedIPEntry  3 }

	assignedIPDelEntry	OBJECT-TYPE
				SYNTAX INTEGER { yes(1), no(2) }
				MAX-ACCESS read-write
				STATUS current
				DESCRIPTION
					"Delete the assigned IP enntry."
				::= { assignedIPEntry 4 }

-- **********************************************************************
-- *  End of DHCP server Config Section 
-- **********************************************************************

-- **********************************************************************
-- *  Route Config Section 
-- **********************************************************************

	route			OBJECT IDENTIFIER ::= { lan 3 }

	enableStaticRoutes	OBJECT-TYPE
                                SYNTAX INTEGER { yes(1), no(2) }
				MAX-ACCESS read-write
                                STATUS current
				DESCRIPTION ""
				::= { route 1 }

	rClientListAct		OBJECT-TYPE
				SYNTAX INTEGER { scan(1), nothing(2) }
				MAX-ACCESS read-write
				STATUS current
				DESCRIPTION ""
				::= { route 2 }

	rClientTable		OBJECT-TYPE
				SYNTAX SEQUENCE OF RClientEntry
				MAX-ACCESS not-accessible
				STATUS current
				DESCRIPTION ""
                                ::= { route 3 }

	rClientEntry		OBJECT-TYPE
				SYNTAX RClientEntry
				MAX-ACCESS not-accessible
				STATUS current
				DESCRIPTION ""
				INDEX { rClientIndex }
				::= { rClientTable 1 }

 	RClientEntry ::= SEQUENCE {
        	rClientIndex    	INTEGER,
        	rClientIPAddr	        OCTET STRING,
        	rClientName		OCTET STRING
    	}

	rClientIndex		OBJECT-TYPE
				SYNTAX INTEGER ( 1..32 )
				MAX-ACCESS not-accessible
				STATUS current
				DESCRIPTION
					"Client entry index."
				::= { rClientEntry 1 }

	rClientIPAddr		OBJECT-TYPE
				SYNTAX OCTET STRING
				MAX-ACCESS read-only
				STATUS current
				DESCRIPTION
					"IP address of the client list."
				::= { rClientEntry 2 }

	rClientName		OBJECT-TYPE
				SYNTAX OCTET STRING
				MAX-ACCESS read-only
				STATUS current
				DESCRIPTION
					"Name of the client list."
				::= { rClientEntry 3 }

	staticRouteTable	OBJECT-TYPE
				SYNTAX SEQUENCE OF StaticRouteEntry
				MAX-ACCESS not-accessible
				STATUS current
				DESCRIPTION
					"Static route list."
				::= { route 4 }

	staticRouteEntry	OBJECT-TYPE
				SYNTAX StaticRouteEntry
				MAX-ACCESS not-accessible
				STATUS current
				DESCRIPTION ""
				INDEX { staticRouteIndex }
				::= { staticRouteTable 1 }

 	StaticRouteEntry ::= SEQUENCE {
        	staticRouteIndex	INTEGER,
        	staticRouteIPAddr	OCTET STRING,
		staticRoutenNetmask	IpAddress,
		staticRouteGateway	IpAddress,
		staticRouteMetric	INTEGER,
		staticRouteInterface	INTEGER,
        	staticRouteDelEntry	INTEGER
    	}                           
    
	staticRouteIndex	OBJECT-TYPE
				SYNTAX INTEGER
				MAX-ACCESS not-accessible
				STATUS current
				DESCRIPTION 
					"Static Route Index."
				::= { staticRouteEntry 1 }

	staticRouteIPAddr	OBJECT-TYPE
				SYNTAX OCTET STRING
				MAX-ACCESS read-write
				STATUS current
				DESCRIPTION
					"IP address of static route list."
				::= { staticRouteEntry 2 }

	staticRouteNetmask	OBJECT-TYPE
				SYNTAX IpAddress
				MAX-ACCESS read-write
				STATUS current
				DESCRIPTION
					"Netmask of static route list."
				::= { staticRouteEntry 3 }

	staticRouteGateway	OBJECT-TYPE
				SYNTAX IpAddress
				MAX-ACCESS read-write
				STATUS current
				DESCRIPTION
					"Netmask of static route list."
				::= { staticRouteEntry 4 }

	staticRouteMetric	OBJECT-TYPE
				SYNTAX INTEGER
				MAX-ACCESS read-write
				STATUS current
				DESCRIPTION
					"Metric of static route list."
				::= { staticRouteEntry 5 }

	staticRouteInterface	OBJECT-TYPE
				SYNTAX INTEGER { lan(1), man(2), wan(3) }
				MAX-ACCESS read-write
				STATUS current
				DESCRIPTION
					"Interface of static route list."
				::= { staticRouteEntry 6 }

	staticRouteDelEntry	OBJECT-TYPE
				SYNTAX INTEGER { yes(1), no(2) }
				MAX-ACCESS read-write
				STATUS current
				DESCRIPTION
					"Delete the static route enntry."
				::= { staticRouteEntry 7 }


-- **********************************************************************
-- *  End of route Config Section 
-- **********************************************************************

-- **********************************************************************
-- *  IPTV Config Section 
-- **********************************************************************

	iptv			OBJECT IDENTIFIER ::= { lan 4 }

	port			OBJECT IDENTIFIER ::= { iptv 1 }

	selectISPProfile	OBJECT-TYPE
				SYNTAX INTEGER { none(1), unifi-home(2), unifi-business(3), singtel-mio(4), singtel-others(5), m1-fiber(6), maxis-fiber(7), maxis-fiber-special(8), manual(9) }
				MAX-ACCESS read-write
				STATUS current
				DESCRIPTION ""
				::= { port 1 }

	iptvSTBPort		OBJECT-TYPE
				SYNTAX INTEGER { none(1), lan1(2), lan2(3), lan3(4), lan4(5), lan1-and-lan2(6), lan3-and-lan4(7) }
				MAX-ACCESS read-write
				STATUS current
				DESCRIPTION ""
				::= { port 2 }

	voipPort		OBJECT-TYPE
                                SYNTAX OCTET STRING
                                MAX-ACCESS read-only
                                STATUS current
                                DESCRIPTION ""
                                ::= { port 3 }
	
--	iInternet		OBJECT IDENTIFIER ::= { port 4 }

	internetVID		OBJECT-TYPE
				SYNTAX INTEGER
				MAX-ACCESS read-write
				STATUS current
				DESCRIPTION ""
				::= { port 4 }

	internetPRIO		OBJECT-TYPE
				SYNTAX INTEGER
				MAX-ACCESS read-write
				STATUS current
				DESCRIPTION ""
				::= { port 5 }

--	lan4Port		OBJECT IDENTIFIER ::= { port 5 }

	lan4PortVID		OBJECT-TYPE
				SYNTAX INTEGER
				MAX-ACCESS read-write
				STATUS current
				DESCRIPTION ""
				::= { port 6 }

	lan4PortPRIO		OBJECT-TYPE
				SYNTAX INTEGER
				MAX-ACCESS read-write
				STATUS current
				DESCRIPTION ""
				::= { port 7 }

--	lan3Port		OBJECT IDENTIFIER ::= { port 6 }

	lan3PortVID		OBJECT-TYPE
				SYNTAX INTEGER
				MAX-ACCESS read-write
				STATUS current
				DESCRIPTION ""
				::= { port 8 }

	lan3PortPRIO		OBJECT-TYPE
				SYNTAX INTEGER
				MAX-ACCESS read-write
				STATUS current
				DESCRIPTION ""
				::= { port 9 }

	special-applications	OBJECT IDENTIFIER ::= { iptv 2 }

	useDHCPRoutes		OBJECT-TYPE
				SYNTAX INTEGER { disable(1), microsoft(2), rfc3442(3), rfc3442-and-microsoft(4) }
				MAX-ACCESS read-write
				STATUS current
				DESCRIPTION ""
				::= { special-applications 1 }

	enableMulticastRouting	OBJECT-TYPE
                                SYNTAX INTEGER { enable(1), disable(2) }
				MAX-ACCESS read-write
				STATUS current                                                        
                                DESCRIPTION
					"Allows the wireless router to handle the multicast packets. Enabling multicast router 
					also enables the RTP and RTSP functions."
                                ::= { special-applications 2 }

	enableEfficientMulticastForwarding	OBJECT-TYPE
                                SYNTAX INTEGER { enable(1), disable(2) }
				MAX-ACCESS read-write
				STATUS current                                                        
                                DESCRIPTION ""
                                ::= { special-applications 3 }

	udpProxy		OBJECT-TYPE
				SYNTAX INTEGER
				MAX-ACCESS read-write
				STATUS current
				DESCRIPTION
					"Use this function to run the IPTV application (such as VLC) on several computers at the 
					same time. This function can convert multicast UDP streams to unicast HTTP streams. Enter 
					the port (such as 4000) that you want to assign for the IPTV application, then use this 
					format to enter the address in the play list to watch IPTV streams: http://[Router IP]:
					[Udpxy port]/[protocol]/[channel IP address]:[channel  port] (such as http://192.168.1.1:
					4000/udp/239.255.1.1:5000 or http://192.168.1.1:4000/rtp/239.255.1.2:5000). Enter 0 (zero) 
					to disable this function."
				::= { special-applications 4 }

-- **********************************************************************
-- *  End of IPTV Config Section 
-- **********************************************************************


-- **********************************************************************
-- *  Switch Control Config Section 
-- **********************************************************************

	switch-control		OBJECT IDENTIFIER ::= { lan 5 }

	enableJumboFrame	OBJECT-TYPE
                                SYNTAX INTEGER { yes(1), no(2) }
				MAX-ACCESS read-write
                                STATUS current
				DESCRIPTION ""
				::= { switch-control 1 }

	enableHWAccelerator	OBJECT-TYPE
                                SYNTAX INTEGER { yes(1), no(2) }
				MAX-ACCESS read-write
                                STATUS current
				DESCRIPTION ""
				::= { switch-control 2 }

--	enableGenericReceiveOffload		OBJECT-TYPE
--                                SYNTAX INTEGER { yes(1), no(2) }
--				MAX-ACCESS read-write
--                                STATUS current
--				DESCRIPTION ""
--				::= { switch-control 3 }

-- **********************************************************************
-- *  End of Switch Control Config Section 
-- **********************************************************************

-- ======================================================================
-- * End of LAN Section
-- ======================================================================





-- ======================================================================
-- * WAN Section
-- ======================================================================

-- **********************************************************************
-- *  Internet Connection Config Section 
-- **********************************************************************
	internet-connection	OBJECT IDENTIFIER ::= { wan 1 }

	basic-config-ic		OBJECT IDENTIFIER ::= { internet-connection 1 }

	wanConnectionType	OBJECT-TYPE
				SYNTAX INTEGER { automatic-ip(1), pppoe(2), static-ip(3), pptp(4), l2tp(5) }
				MAX-ACCESS read-write
				STATUS current
				DESCRIPTION ""
				::= { basic-config-ic 1 }

	enableWAN		OBJECT-TYPE
				SYNTAX INTEGER { yes(1), no(2) }
				MAX-ACCESS read-write
				STATUS current
				DESCRIPTION ""
				::= { basic-config-ic 2 }

	enableNAT		OBJECT-TYPE
				SYNTAX INTEGER { yes(1), no(2) }
				MAX-ACCESS read-write
				STATUS current
				DESCRIPTION
					"NAT (Network Address Translation) is a process used in routers to replace the address 
					information of network packet with new address information. Typical applications for NAT 
					is router which connect to LAN with the WAN. In LAN every network devices had a private 
					IP(LAN IP) but there is only one public IP(WAN IP). To grant the network devices access 
					to the Internet, the router replaces the private IP address of the sender with its own 
					public IP address in all outgoing data packets. The router saves all necessary information 
					in a table(NAT table) so that incoming data packets can then be assigned on the correct 
					network device."
				::= { basic-config-ic 3 }

	enableUPnP		OBJECT-TYPE
				SYNTAX INTEGER { yes(1), no(2) }
				MAX-ACCESS read-write
				STATUS current
				DESCRIPTION
					"UPnP (Universal Plug and Play) allows several devices (routers, televisions, stereo 
					systems, game consoles, cellular phone) to be controlled via an IP-based network with or 
					without a central control through a gateway."
				::= { basic-config-ic 4 }

	wan-ip-setting		OBJECT IDENTIFIER ::= { internet-connection 2 }

	getWanIPAuto		OBJECT-TYPE
				SYNTAX INTEGER { yes(1), no(2) }
				MAX-ACCESS read-write
				STATUS current
				DESCRIPTION ""
				::= { wan-ip-setting 1 }

	wIPAddress		OBJECT-TYPE
				SYNTAX IpAddress
				MAX-ACCESS read-write
				STATUS current
				DESCRIPTION
		                       "If your WAN connection requires a static IP address, key in the IP address in this field."
                                ::= { wan-ip-setting 2 }

	wSubnetMask		OBJECT-TYPE
				SYNTAX IpAddress
				MAX-ACCESS read-write
				STATUS current
				DESCRIPTION
					"If your WAN connection requires a static IP address, key in the subnet mask in this field."
				::= { wan-ip-setting 3 }

	wDefaultGateway		OBJECT-TYPE
				SYNTAX IpAddress
				MAX-ACCESS read-write
				STATUS current
				DESCRIPTION
					"If your WAN connection requires a static IP address, key in the gateway IP address in this 
					field."
				::= { wan-ip-setting 4 }

	wan-dns-setting		OBJECT IDENTIFIER ::= { internet-connection 3 }

	connectDNSServerAuto	OBJECT-TYPE
				SYNTAX INTEGER { yes(1), no(2) }
				MAX-ACCESS read-write
				STATUS current
				DESCRIPTION
					"Allows this router to get the DNS IP address from the ISP automatically."
				::= { wan-dns-setting 1 }

	dnsServer1		OBJECT-TYPE
                                SYNTAX IpAddress
                                MAX-ACCESS read-write
                                STATUS current
                                DESCRIPTION
					"This field indicates the IP address of DNS that RT-N12 contact to."
                                ::= { wan-dns-setting 2 }

	dnsServer2		OBJECT-TYPE
                                SYNTAX IpAddress
                                MAX-ACCESS read-write
                                STATUS current
                                DESCRIPTION
					"This field indicates the IP address of DNS that RT-N12 contact to."
                                ::= { wan-dns-setting 3 }

	account-setting		OBJECT IDENTIFIER ::= { internet-connection 4 }

	wAuthentication		OBJECT-TYPE
				SYNTAX INTEGER { none(1), 802dot1x-md5(2) }
				MAX-ACCESS read-write
				STATUS current
				DESCRIPTION ""
				::= { account-setting 1 }

	wUserName		OBJECT-TYPE
                                SYNTAX OCTET STRING ( SIZE (1..64) )
                                MAX-ACCESS read-write
                                STATUS current
                                DESCRIPTION
					"This field is only available when you set the WAN Connection Type as USB Modem, PPPoE, 
					PPTP or L2TP."
                                ::= { account-setting 2 }

	wPassword		OBJECT-TYPE
                                SYNTAX OCTET STRING ( SIZE (1..64) )
                                MAX-ACCESS read-write
                                STATUS current
                                DESCRIPTION
					"This field is only available when you set WAN Connection Type as PPPoE."
                                ::= { account-setting 3 }

	idleDisconnectTime	OBJECT-TYPE
				SYNTAX INTEGER
				MAX-ACCESS read-write
				STATUS current
				DESCRIPTION
					"This field is optional and allows you to configure to terminate your ISP connection after 
					a specified period of time. A value of zero allows infinite idle time."
				::= { account-setting 4 }

	mtu			OBJECT-TYPE
				SYNTAX INTEGER
				MAX-ACCESS read-write
				STATUS current
				DESCRIPTION
					"The Maximum Transmission Unit (MTU) of PPPoE packet. The default value is 1492. Change this 
					value only if your ISP requires it."
				::= { account-setting 5 }

	mru			OBJECT-TYPE
				SYNTAX INTEGER
				MAX-ACCESS read-write
				STATUS current
				DESCRIPTION
					"The Maximum Receive Unit (MRU) of PPPoE packet. The default value is 1492. Change this value 
					only if your ISP requires it."
				::= { account-setting 6 }

	serviceName		OBJECT-TYPE
                                SYNTAX OCTET STRING ( SIZE (1..32) )
                                MAX-ACCESS read-write
                                STATUS current
                                DESCRIPTION
					"This field is optional and may be specified by some ISPs. Check with your ISP and fill them 
					in if required."
                                ::= { account-setting 7 }

	accessConcentratorName		OBJECT-TYPE
                                SYNTAX OCTET STRING ( SIZE (1..32) )
                                MAX-ACCESS read-write
                                STATUS current
                                DESCRIPTION
					"This field is optional and may be specified by some ISPs. Check with your ISP and fill them 
					in if required."
                                ::= { account-setting 8 }

	pptpOptions		OBJECT-TYPE
				SYNTAX INTEGER { auto(1), no-encryption(2), mppe-40(3), mppe-128(4) }
				MAX-ACCESS read-write
				STATUS current
				DESCRIPTION
					"This field is optional and may be specified by some ISPs. Check with your ISP and fill them 
					in if required."
				::= { account-setting 9 }

	additionalPppdOptions		OBJECT-TYPE
                                SYNTAX OCTET STRING ( SIZE (1..32) )
                                MAX-ACCESS read-write
                                STATUS current
                                DESCRIPTION
					"This field is optional and may be specified by some ISPs. Check with your ISP and fill them 
					in if required."
                                ::= { account-setting 10 }

	special-requirement-from-ISP	OBJECT IDENTIFIER ::= { internet-connection 5 }

	vpnServer		OBJECT-TYPE
                                SYNTAX OCTET STRING ( SIZE (1..256) )
                                MAX-ACCESS read-write
                                STATUS current
                                DESCRIPTION
					"If your WAN connection type is PPTP or L2TP, Please enter the server name or server ip of the 
					VPN server."
                                ::= { special-requirement-from-ISP 1 }

	enableVPNandDHCPConnection		OBJECT-TYPE
				SYNTAX INTEGER { yes(1), no(2) }
				MAX-ACCESS read-write
				STATUS current
				DESCRIPTION ""
				::= { special-requirement-from-ISP 2 }

	wHostName		OBJECT-TYPE
                                SYNTAX OCTET STRING ( SIZE (1..32) )
                                MAX-ACCESS read-write
                                STATUS current
                                DESCRIPTION
					"This field allows you to provide a host name for RT-N12. It is usually requested by your ISP."
                                ::= { special-requirement-from-ISP 3 }

	wMacAddress	OBJECT-TYPE
				SYNTAX MacAddress
				MAX-ACCESS read-write
				STATUS current
				DESCRIPTION
					"MAC (Media Access Control) address is a unique identifier that identifies your computer or 
					device in the network. ISPs monitor the MAC addresses of devices that connect to their services, 
					and would disallow Internet connection for new MAC addresses. To fix this issue, you can do 
					either of the following: *Contact your ISP and request to update the MAC address associated 
					with your ISP subscription. *Clone or change the MAC address of the new device to match the 
					MAC address of the original device."
				::= { special-requirement-from-ISP  4 }

	dhcpQueryRrequency	OBJECT-TYPE
				SYNTAX INTEGER { normal-mode(1), aggressive-mode(2) }
				MAX-ACCESS read-write
				STATUS current
				DESCRIPTION ""
				::= { special-requirement-from-ISP 5 }

-- **********************************************************************
-- *  End of Internet Connection Config Section 
-- **********************************************************************

-- **********************************************************************
-- *  Port Trigger Config Section 
-- **********************************************************************

	port-trigger		OBJECT IDENTIFIER ::= { wan 2 }

	enablePortTrigger	OBJECT-TYPE
				SYNTAX INTEGER { yes(1), no(2) }
				MAX-ACCESS read-write
				STATUS current
				DESCRIPTION ""
				::= { port-trigger 1 }

	portTriggerTable	OBJECT-TYPE
				SYNTAX SEQUENCE OF PortTriggerEntry
				MAX-ACCESS not-accessible
				STATUS current
				DESCRIPTION
					"Prt tirgger list."
				::= { port-trigger 2 }

	portTriggerEntry	OBJECT-TYPE
				SYNTAX PortTriggerEntry
				MAX-ACCESS not-accessible
				STATUS current
				DESCRIPTION ""
				INDEX { portTriggerIndex }
				::= { portTriggerTable 1 }

 	PortTriggerEntry ::= SEQUENCE {
        	portTriggerIndex		INTEGER,
		portTriggerDescription		OCTET STRING,
		portTriggerPort			OCTET STRING,
		portTriggerProtocol		INTEGER,
		portTriggerIncomingPort		OCTET STRING,
		portTriggerIncomingProtocol	INTEGER,
        	portTriggerDelEntry		INTEGER
    	}                           
    
	portTriggerIndex	OBJECT-TYPE
				SYNTAX INTEGER
				MAX-ACCESS not-accessible
				STATUS current
				DESCRIPTION 
					"Port trigger index."
				::= { portTriggerEntry 1 }

	portTriggerDescription	OBJECT-TYPE
				SYNTAX OCTET STRING ( SIZE (1..18) )
				MAX-ACCESS read-write
				STATUS current
				DESCRIPTION
					"Description of port trigger list."
				::= { portTriggerEntry 2 }

	portTriggerPort		OBJECT-TYPE
				SYNTAX OCTET STRING ( SIZE (1..11) )
				MAX-ACCESS read-write
				STATUS current
				DESCRIPTION
					"Port of port trigger list."
				::= { portTriggerEntry 3 }

	portTriggerProtocol	OBJECT-TYPE
				SYNTAX INTEGER { tcp(1), udp(2) }
				MAX-ACCESS read-write
				STATUS current
				DESCRIPTION
					"Protocol of port trigger list."
				::= { portTriggerEntry 4 }

	portTriggerIncomingPort		OBJECT-TYPE
				SYNTAX OCTET STRING ( SIZE (1..11) )
				MAX-ACCESS read-write
				STATUS current
				DESCRIPTION
					"Incoming port of port trigger list."
				::= { portTriggerEntry 5 }

	portTriggerIncomingProtocol	OBJECT-TYPE
				SYNTAX INTEGER { tcp(1), udp(2) }
				MAX-ACCESS read-write
				STATUS current
				DESCRIPTION
					"Incoming protocol of port trigger list."
				::= { portTriggerEntry 6 }

	portTriggerDelEntry	OBJECT-TYPE
				SYNTAX INTEGER { yes(1), no(2) }
				MAX-ACCESS read-write
				STATUS current
				DESCRIPTION
					"Delete the port trigger enntry."
				::= { portTriggerEntry 7 }

-- **********************************************************************
-- *  End of Port Trigger Config Section 
-- **********************************************************************

-- **********************************************************************
-- *  Virtual server / Port Forwarding Config Section 
-- **********************************************************************

	port-forwarding		OBJECT IDENTIFIER ::= { wan 3 }

	enablePortForwarding	OBJECT-TYPE
				SYNTAX INTEGER { yes(1), no(2) }
				MAX-ACCESS read-write
				STATUS current
				DESCRIPTION ""
				::= { port-forwarding 1 }

	ftpServerPort		OBJECT-TYPE
				SYNTAX INTEGER ( 1..65535 )
				MAX-ACCESS read-write
				STATUS current
				DESCRIPTION ""
				::= { port-forwarding 2 }

	wClientListAct		OBJECT-TYPE
				SYNTAX INTEGER { scan(1), nothing(2) }
				MAX-ACCESS read-write
				STATUS current
				DESCRIPTION ""
				::= { port-forwarding 3 }

	wClientTable		OBJECT-TYPE
				SYNTAX SEQUENCE OF WClientEntry
				MAX-ACCESS not-accessible
				STATUS current
				DESCRIPTION ""
                                ::= { port-forwarding 4 }

	wClientEntry		OBJECT-TYPE
				SYNTAX WClientEntry
				MAX-ACCESS not-accessible
				STATUS current
				DESCRIPTION ""
				INDEX { wClientIndex }
				::= { wClientTable 1 }

 	WClientEntry ::= SEQUENCE {
        	wClientIndex    	INTEGER,
        	wClientIPAddr	        IpAddress,
        	wClientName		OCTET STRING
    	}

	wClientIndex		OBJECT-TYPE
				SYNTAX INTEGER ( 1..32 )
				MAX-ACCESS not-accessible
				STATUS current
				DESCRIPTION
					"Client entry index."
				::= { wClientEntry 1 }

	wClientIPAddr		OBJECT-TYPE
				SYNTAX IpAddress
				MAX-ACCESS read-only
				STATUS current
				DESCRIPTION
					"MAC address of the client list."
				::= { wClientEntry 2 }

	wClientName		OBJECT-TYPE
				SYNTAX OCTET STRING
				MAX-ACCESS read-only
				STATUS current
				DESCRIPTION
					"Name of the client list."
				::= { wClientEntry 3 }

	portForwardingTable	OBJECT-TYPE
				SYNTAX SEQUENCE OF PortForwardingEntry
				MAX-ACCESS not-accessible
				STATUS current
				DESCRIPTION
					"Port forwarding list."
				::= { port-forwarding 5 }

	portForwardingEntry	OBJECT-TYPE
				SYNTAX PortForwardingEntry
				MAX-ACCESS not-accessible
				STATUS current
				DESCRIPTION ""
				INDEX { portForwardingIndex }
				::= { portForwardingTable 1 }

 	PortForwardingEntry ::= SEQUENCE {
        	portForwardingIndex		INTEGER,
		portForwardingServiceName	OCTET STRING,
		portForwardingPortRange		OCTET STRING,
		portForwardingLocalIP		IpAddress,
		portForwardingLocalPort		INTEGER,
		portForwardingProtocol		INTEGER,
        	portForwardingDelEntry		INTEGER
    	}                           
    
	portForwardingIndex	OBJECT-TYPE
				SYNTAX INTEGER
				MAX-ACCESS not-accessible
				STATUS current
				DESCRIPTION 
					"Port Forwarding Index."
				::= { portForwardingEntry 1 }

	portForwardingServiceName	OBJECT-TYPE
				SYNTAX OCTET STRING ( SIZE (1..30) )
				MAX-ACCESS read-write
				STATUS current
				DESCRIPTION
					"Service name of port forwarding list."
				::= { portForwardingEntry 2 }

	portForwardingPortRange		OBJECT-TYPE
				SYNTAX OCTET STRING
				MAX-ACCESS read-write
				STATUS current
				DESCRIPTION
					"Port range of port forwarding list."
				::= { portForwardingEntry 3 }

	portForwardingLocalIP		OBJECT-TYPE
				SYNTAX IpAddress
				MAX-ACCESS read-write
				STATUS current
				DESCRIPTION
					"Local IP of port forwarding list."
				::= { portForwardingEntry 4 }

	portForwardingLocalPort	OBJECT-TYPE
				SYNTAX INTEGER (1..65535)
				MAX-ACCESS read-write
				STATUS current
				DESCRIPTION
					"Local port of port forwarding list."
				::= { portForwardingEntry 5 }

	portForwardingProtocol	OBJECT-TYPE
				SYNTAX INTEGER { tcp(1), udp(2), both(3), other(4) }
				MAX-ACCESS read-write
				STATUS current
				DESCRIPTION
					"Protocol of port forwarding list."
				::= { portForwardingEntry 6 }

	portForwardingDelEntry	OBJECT-TYPE
				SYNTAX INTEGER { yes(1), no(2) }
				MAX-ACCESS read-write
				STATUS current
				DESCRIPTION
					"Delete the port forwarding entry."
				::= { portForwardingEntry 7 }

-- **********************************************************************
-- *  End of Virtual server / Port Forwarding Config Section 
-- **********************************************************************

-- **********************************************************************
-- *   DMZ Config Section 
-- **********************************************************************

	dmz		OBJECT IDENTIFIER ::= { wan 4 }

	exposedStationIPAddr		OBJECT-TYPE
				SYNTAX IpAddress
				MAX-ACCESS read-write
				STATUS current
				DESCRIPTION ""
				::= { dmz 1 }

-- **********************************************************************
-- *  End of DMZ Config Section 
-- **********************************************************************

-- **********************************************************************
-- *   DDNS Config Section 
-- **********************************************************************

	ddns			OBJECT IDENTIFIER ::= { wan 5 }

	enableDDNSClient	OBJECT-TYPE
				SYNTAX INTEGER { yes(1), no(2) }
				MAX-ACCESS read-write
				STATUS current
				DESCRIPTION ""
				::= { ddns 1 }

	ddnsServer		OBJECT-TYPE
				SYNTAX INTEGER { asus(1), dyndns(2), dyndns-custom(3), dyndns-static(4), tzo(5), zoneedit(6), dnsmatic(7), tunnelbroker(8), no-ip(9) }
				MAX-ACCESS read-write
				STATUS current
				DESCRIPTION ""
				::= { ddns 2 }

	ddnsHostName		OBJECT-TYPE
                                SYNTAX OCTET STRING ( SIZE (1..63) )
                                MAX-ACCESS read-write
                                STATUS current
                                DESCRIPTION
					"The host name cannot accept number prefix and '.' (such as '123abc' or 'aaa.bbb')."
                                ::= { ddns 3 }

	ddnsUserNameOrMail	OBJECT-TYPE
                                SYNTAX OCTET STRING ( SIZE (1..32) )
                                MAX-ACCESS read-write
                                STATUS current
                                DESCRIPTION ""
                                ::= { ddns 4 }

	ddnsPasswordOrKey	OBJECT-TYPE
                                SYNTAX OCTET STRING ( SIZE (1..64) )
                                MAX-ACCESS read-write
                                STATUS current
                                DESCRIPTION ""
                                ::= { ddns 5 }

	enableWildcard		OBJECT-TYPE
				SYNTAX INTEGER { yes(1), no(2) }
				MAX-ACCESS read-write
				STATUS current
				DESCRIPTION ""
				::= { ddns 6 }

-- **********************************************************************
-- *  End of DDNS Config Section 
-- **********************************************************************

-- **********************************************************************
-- *   NAT Passthrough Config Section 
-- **********************************************************************

	nat-passthrough		OBJECT IDENTIFIER ::= { wan 6 }

	pptpPassthrough		OBJECT-TYPE
				SYNTAX INTEGER { enable(1), disable(2) }
				MAX-ACCESS read-write
				STATUS current
				DESCRIPTION ""
				::= { nat-passthrough 1 }

	l2tpPassthrough		OBJECT-TYPE
				SYNTAX INTEGER { enable(1), disable(2) }
				MAX-ACCESS read-write
				STATUS current
				DESCRIPTION ""
				::= { nat-passthrough 2 }

	ipsecPassthrough		OBJECT-TYPE
				SYNTAX INTEGER { enable(1), disable(2) }
				MAX-ACCESS read-write
				STATUS current
				DESCRIPTION ""
				::= { nat-passthrough 3 }

	rtspPassthrough		OBJECT-TYPE
				SYNTAX INTEGER { enable(1), disable(2) }
				MAX-ACCESS read-write
				STATUS current
				DESCRIPTION ""
				::= { nat-passthrough 4 }

	h323Passthrough		OBJECT-TYPE
				SYNTAX INTEGER { enable(1), disable(2) }
				MAX-ACCESS read-write
				STATUS current
				DESCRIPTION ""
				::= { nat-passthrough 5 }

	sipPassthrough		OBJECT-TYPE
				SYNTAX INTEGER { enable(1), disable(2) }
				MAX-ACCESS read-write
				STATUS current
				DESCRIPTION ""
				::= { nat-passthrough 6 }

	pppoeRelay		OBJECT-TYPE
				SYNTAX INTEGER { enable(1), disable(2) }
				MAX-ACCESS read-write
				STATUS current
				DESCRIPTION
					"Enable PPPoE relay allows devices in LAN to establish a individual PPPoE connections that 
					passes through NAT."
				::= { nat-passthrough 7 }

-- **********************************************************************
-- *  End of NAT Passthrough Config Section 
-- **********************************************************************

-- ======================================================================
-- * End of WAN Section
-- ======================================================================





-- ======================================================================
-- * IPv6 Section
-- ======================================================================

-- **********************************************************************
-- *  IPv6 Config Section 
-- **********************************************************************
	basic-config-ipv6	OBJECT IDENTIFIER ::= { ipv6 1 }

	connectionType		OBJECT-TYPE
				SYNTAX INTEGER { disable(1), native-with-dhcp-pd(2), tunnel-6to4(3), tunnel-6in4(4), tunnel-6rd(5), static-ipv6(6) }
				MAX-ACCESS read-write
				STATUS current
				DESCRIPTION ""
				::= { basic-config-ipv6 1 }

	serverIPv4Address	OBJECT-TYPE
				SYNTAX IpAddress
				MAX-ACCESS read-write
				STATUS current
				DESCRIPTION ""
				::= { basic-config-ipv6 2 }

	ipv4AnycastRelay	OBJECT-TYPE
				SYNTAX IpAddress
				MAX-ACCESS read-write
				STATUS current
				DESCRIPTION ""
				::= { basic-config-ipv6 3 }

	dhcpOption		OBJECT-TYPE
				SYNTAX INTEGER { enable(1), disable(2) }
				MAX-ACCESS read-write
				STATUS current
				DESCRIPTION ""
				::= { basic-config-ipv6 4 }

	ipv6Prefix		OBJECT-TYPE
				SYNTAX OCTET STRING ( SIZE (1..39) )
				MAX-ACCESS read-write
				STATUS current
				DESCRIPTION ""
                                ::= { basic-config-ipv6 5 }

	ipv6PrefixLength6rd	OBJECT-TYPE
				SYNTAX INTEGER
				MAX-ACCESS read-write
				STATUS current
				DESCRIPTION ""
				::= { basic-config-ipv6 6 }

	ipv4BorderRouter	OBJECT-TYPE
				SYNTAX IpAddress
				MAX-ACCESS read-write
				STATUS current
				DESCRIPTION ""
				::= { basic-config-ipv6 7 }

	ipv4RouterMaskLength	OBJECT-TYPE
				SYNTAX INTEGER
				MAX-ACCESS read-write
				STATUS current
				DESCRIPTION ""
				::= { basic-config-ipv6 8 }

	clientIPv6Address	OBJECT-TYPE
				SYNTAX OCTET STRING ( SIZE (1..39) )
				MAX-ACCESS read-write
				STATUS current
				DESCRIPTION ""
                                ::= { basic-config-ipv6 9 }

	ipv6PrefixLength6in4	OBJECT-TYPE
				SYNTAX INTEGER
				MAX-ACCESS read-write
				STATUS current
				DESCRIPTION ""
				::= { basic-config-ipv6 10 }

	tunnelMTU		OBJECT-TYPE
				SYNTAX INTEGER
				MAX-ACCESS read-write
				STATUS current
				DESCRIPTION ""
				::= { basic-config-ipv6 11 }

	tunnelTTL		OBJECT-TYPE
				SYNTAX INTEGER
				MAX-ACCESS read-write
				STATUS current
				DESCRIPTION ""
				::= { basic-config-ipv6 12 }	

	wan-setting-ipv6	OBJECT IDENTIFIER ::= { ipv6 2 }

	wanIPv6Address		OBJECT-TYPE
				SYNTAX OCTET STRING ( SIZE (1..39) )
				MAX-ACCESS read-write
				STATUS current
				DESCRIPTION ""
                                ::= { wan-setting-ipv6 1 }

	wanPrefixLength		OBJECT-TYPE
				SYNTAX INTEGER
				MAX-ACCESS read-write
				STATUS current
				DESCRIPTION ""
				::= { wan-setting-ipv6 2 }

	wanIPv6Gateway		OBJECT-TYPE
				SYNTAX OCTET STRING ( SIZE (1..39) )
				MAX-ACCESS read-write
				STATUS current
				DESCRIPTION ""
                                ::= { wan-setting-ipv6 3 }

	lan-setting-ipv6	OBJECT IDENTIFIER ::= { ipv6 3 }

	lanIPv6Prefix		OBJECT-TYPE
				SYNTAX OCTET STRING ( SIZE (1..39) )
				MAX-ACCESS read-write
				STATUS current
				DESCRIPTION ""
                                ::= { lan-setting-ipv6 1 }

	lanPrefixLength		OBJECT-TYPE
				SYNTAX INTEGER
				MAX-ACCESS read-write
				STATUS current
				DESCRIPTION ""
				::= { lan-setting-ipv6 2 }

	lanIPv6Address		OBJECT-TYPE
				SYNTAX OCTET STRING ( SIZE (1..39) )
				MAX-ACCESS read-write
				STATUS current
				DESCRIPTION ""
                                ::= { lan-setting-ipv6 3 }

	dns-setting-ipv6	OBJECT IDENTIFIER ::= { ipv6 4 }

	ipv6ConnectToDNSServerAuto	OBJECT-TYPE
				SYNTAX INTEGER { yes(1), no(2) }
				MAX-ACCESS read-write
				STATUS current
				DESCRIPTION
					"Allows this router to get the DNS IP address from the ISP automatically."
				::= { dns-setting-ipv6 1 }

	ipv6DNSServer1		OBJECT-TYPE
				SYNTAX OCTET STRING ( SIZE (1..39) )
				MAX-ACCESS read-write
				STATUS current
				DESCRIPTION ""
                                ::= { dns-setting-ipv6 2 }
	ipv6DNSServer2		OBJECT-TYPE
				SYNTAX OCTET STRING ( SIZE (1..39) )
				MAX-ACCESS read-write
				STATUS current
				DESCRIPTION ""
                                ::= { dns-setting-ipv6 3 }

	ipv6DNSServer3		OBJECT-TYPE
				SYNTAX OCTET STRING ( SIZE (1..39) )
				MAX-ACCESS read-write
				STATUS current
				DESCRIPTION ""
                                ::= { dns-setting-ipv6 4 }
	

	auto-configuration-setting	OBJECT IDENTIFIER ::= { ipv6 5 }

	enableRouterAdvertisement		OBJECT-TYPE
				SYNTAX INTEGER { enable(1), disable(2) }
				MAX-ACCESS read-write
				STATUS current
				DESCRIPTION ""
				::= { auto-configuration-setting 1 }

-- **********************************************************************
-- *  End of IPv6 Config Section 
-- **********************************************************************





-- ======================================================================
-- * VPN Server Section
-- ======================================================================

-- **********************************************************************
-- *  VPN Server Section 
-- **********************************************************************

	vpn-server-setting	OBJECT IDENTIFIER ::= { vpn-server 1 }

	basic-config-vpn	OBJECT IDENTIFIER ::= { vpn-server-setting 1 }

	enablePPTPServer	OBJECT-TYPE
				SYNTAX INTEGER { yes(1), no(2) }
				MAX-ACCESS read-write
				STATUS current
				DESCRIPTION ""
				::= { basic-config-vpn 1 }

--	sambaSupport		OBJECT-TYPE
--				SYNTAX INTEGER { yes(1), no(2) }
--				MAX-ACCESS read-write
--				STATUS current
--				DESCRIPTION ""
--				::= { basic-config-vpn 2 }

	username-and-password	OBJECT IDENTIFIER ::= { vpn-server-setting 2 }

	vpnUserTable		OBJECT-TYPE
				SYNTAX SEQUENCE OF VpnUserEntry
				MAX-ACCESS not-accessible
				STATUS current
				DESCRIPTION
					"VPN user list."
				::= { username-and-password 1 }

	vpnUserEntry		OBJECT-TYPE
				SYNTAX VpnUserEntry
				MAX-ACCESS not-accessible
				STATUS current
				DESCRIPTION ""
				INDEX { vpnUserIndex }
				::= { vpnUserTable 1 }

 	VpnUserEntry ::= SEQUENCE {
        	vpnUserIndex		INTEGER,
		vpnUserUserName		OCTET STRING,
		vpnUserPassword		OCTET STRING,
        	vpnUserDelEntry		INTEGER
    	}                           
    
	vpnUserIndex	OBJECT-TYPE
				SYNTAX INTEGER
				MAX-ACCESS not-accessible
				STATUS current
				DESCRIPTION 
					"VPN user index."
				::= { vpnUserEntry 1 }

	vpnUserUserName	OBJECT-TYPE
				SYNTAX OCTET STRING ( SIZE (1..32) )
				MAX-ACCESS read-write
				STATUS current
				DESCRIPTION
					"User name of vpn user list."
				::= { vpnUserEntry 2 }

	vpnUserPassword		OBJECT-TYPE
				SYNTAX OCTET STRING ( SIZE (1..16) )
				MAX-ACCESS read-write
				STATUS current
				DESCRIPTION
					"Password of vpn user list."
				::= { vpnUserEntry 3 }

	vpnUserDelEntry	OBJECT-TYPE
				SYNTAX INTEGER { yes(1), no(2) }
				MAX-ACCESS read-write
				STATUS current
				DESCRIPTION
					"Delete the vpn user enntry."
				::= { vpnUserEntry 4 }

-- **********************************************************************
-- *  End of VPN Server Config Section 
-- **********************************************************************

-- **********************************************************************
-- *  VPN Details Section 
-- **********************************************************************
	vpn-details		OBJECT IDENTIFIER ::= { vpn-server 2 }

	broadcastSupport	OBJECT-TYPE
				SYNTAX INTEGER { disable(1), lan-to-vpn-client(2), vpn-client-to-lan(3), both(4) }
				MAX-ACCESS read-write
				STATUS current
				DESCRIPTION ""
				::= { vpn-details 1 }

	vAuthentication		OBJECT-TYPE
				SYNTAX INTEGER { auto(1), ms-chapv1(2), ms-chapv2(3) }
				MAX-ACCESS read-write
				STATUS current
				DESCRIPTION ""
				::= { vpn-details 2 }

	mppeEncryption		OBJECT-TYPE
				SYNTAX BITS { mppe-128(0), mppe-40(1), no-encryption(2) }
				MAX-ACCESS read-write
				STATUS current
				DESCRIPTION ""
				::= { vpn-details 3 }

	connectToDNSServerAuto	OBJECT-TYPE
				SYNTAX INTEGER { yes(1), no(2) }
				MAX-ACCESS read-write
				STATUS current
				DESCRIPTION ""
				::= { vpn-details 4 }

	vDNSServer1		OBJECT-TYPE
				SYNTAX IpAddress
				MAX-ACCESS read-write
				STATUS current
				DESCRIPTION ""
				::= { vpn-details 5 }

	vDNSServer2		OBJECT-TYPE
				SYNTAX IpAddress
				MAX-ACCESS read-write
				STATUS current
				DESCRIPTION ""
				::= { vpn-details 6 }

	connectToWINSServerAuto	OBJECT-TYPE
				SYNTAX INTEGER { yes(1), no(2) }
				MAX-ACCESS read-write
				STATUS current
				DESCRIPTION ""
				::= { vpn-details 7 }

	vWINSServer1		OBJECT-TYPE
				SYNTAX IpAddress
				MAX-ACCESS read-write
				STATUS current
				DESCRIPTION ""
				::= { vpn-details 8 }

	vWINSServer2		OBJECT-TYPE
				SYNTAX IpAddress
				MAX-ACCESS read-write
				STATUS current
				DESCRIPTION ""
				::= { vpn-details 9 }

	clientStartIPAddress	OBJECT-TYPE
				SYNTAX IpAddress
				MAX-ACCESS read-write
				STATUS current
				DESCRIPTION ""
				::= { vpn-details 10 }

	clientEndIPAddress	OBJECT-TYPE
				SYNTAX INTEGER ( 1..255 )
				MAX-ACCESS read-write
				STATUS current
				DESCRIPTION ""
				::= { vpn-details 11 }

-- **********************************************************************
-- *  End of VPN Details Config Section 
-- **********************************************************************

-- ======================================================================
-- * End of VPN Server Section
-- ======================================================================





-- ======================================================================
-- * Firewall Section
-- ======================================================================

-- **********************************************************************
-- *  General Section 
-- **********************************************************************

	firewall-general	OBJECT IDENTIFIER ::= { firewall 1 }

	enableFirewall		OBJECT-TYPE
				SYNTAX INTEGER { yes(1), no(2) }
				MAX-ACCESS read-write
				STATUS current
				DESCRIPTION
					"Disabling the firewall will deactivate all the related functions."
				::= { firewall-general 1 }

	enableDoSProtection	OBJECT-TYPE
				SYNTAX INTEGER { yes(1), no(2) }
				MAX-ACCESS read-write
				STATUS current
				DESCRIPTION
					"A 'denial-of-service' attack is an explicit attempt to deny legitimate users from using 
					a service or computer resource. Enabling this feature can protect the router from DoS attack 
					but it would increase the router's workload."
				::= { firewall-general 2 }

	loggedPacketsType	OBJECT-TYPE
				SYNTAX INTEGER { none(1), drop(2), accept(3), both(4) }
				MAX-ACCESS read-write
				STATUS current
				DESCRIPTION
					"This field indicates the kind of packets logged between LAN and WAN."
				::= { firewall-general 3 }

	respondPingRequestfromWAN	OBJECT-TYPE
				SYNTAX INTEGER { yes(1), no(2) }
				MAX-ACCESS read-write
				STATUS current
				DESCRIPTION
					"This feature allows you to respond to ping request from WAN."
				::= { firewall-general 4 }

-- **********************************************************************
-- *  End of General Config Section 
-- **********************************************************************

-- **********************************************************************
-- *  URL Filter Section 
-- **********************************************************************

	url-filter		OBJECT IDENTIFIER ::= { firewall 2 }

	basic-config-url	OBJECT IDENTIFIER ::= { url-filter 1 }

	enableURLFilter		OBJECT-TYPE
				SYNTAX INTEGER { enable(1), disable(2) }
				MAX-ACCESS read-write
				STATUS current
				DESCRIPTION
					"This field defines the dates that URL filter will be enabled."
				::= { basic-config-url 1 }

	url-filter-list		OBJECT IDENTIFIER ::= { url-filter 2 }

	urlFilterTable		OBJECT-TYPE
				SYNTAX SEQUENCE OF UrlFilterEntry
				MAX-ACCESS not-accessible
				STATUS current
				DESCRIPTION
					"URL filter list."
				::= { url-filter-list 1 }

	urlFilterEntry		OBJECT-TYPE
				SYNTAX UrlFilterEntry
				MAX-ACCESS not-accessible
				STATUS current
				DESCRIPTION ""
				INDEX { urlFilterIndex }
				::= { urlFilterTable 1 }

 	UrlFilterEntry ::= SEQUENCE {
        	urlFilterIndex		INTEGER,
		urlFilterUrl		OCTET STRING,
        	urlFilterDelEntry	INTEGER
    	}                           
    
	urlFilterIndex		OBJECT-TYPE
				SYNTAX INTEGER
				MAX-ACCESS not-accessible
				STATUS current
				DESCRIPTION 
					"URL Filter Index."
				::= { urlFilterEntry 1 }

	urlFilterUrl		OBJECT-TYPE
				SYNTAX OCTET STRING ( SIZE (1..32) )
				MAX-ACCESS read-write
				STATUS current
				DESCRIPTION
					"URL of url filter list."
				::= { urlFilterEntry 2 }

	urlFilterDelEntry	OBJECT-TYPE
				SYNTAX INTEGER { yes(1), no(2) }
				MAX-ACCESS read-write
				STATUS current
				DESCRIPTION
					"Delete the url filter enntry."
				::= { urlFilterEntry 3 }

-- **********************************************************************
-- *  End of URL Filter Config Section 
-- **********************************************************************

-- **********************************************************************
-- *  Keyword Filter Section 
-- **********************************************************************

	keyword-filter	OBJECT IDENTIFIER ::= { firewall 3 }

	basic-config-keyword	OBJECT IDENTIFIER ::= { keyword-filter 1 }

	enableKeywordFilter	OBJECT-TYPE
				SYNTAX INTEGER { enable(1), disable(2) }
				MAX-ACCESS read-write
				STATUS current
				DESCRIPTION ""
				::= { basic-config-keyword 1 }

	keyword-filter-list	OBJECT IDENTIFIER ::= { keyword-filter 2 }

	keywordFilterTable	OBJECT-TYPE
				SYNTAX SEQUENCE OF KeywordFilterEntry
				MAX-ACCESS not-accessible
				STATUS current
				DESCRIPTION
					"Keyword filter list."
				::= { keyword-filter-list 1 }

	keywordFilterEntry	OBJECT-TYPE
				SYNTAX KeywordFilterEntry
				MAX-ACCESS not-accessible
				STATUS current
				DESCRIPTION ""
				INDEX { keywordFilterIndex }
				::= { keywordFilterTable 1 }

 	KeywordFilterEntry ::= SEQUENCE {
        	keywordFilterIndex		INTEGER,
		keywordFilterKeyword		OCTET STRING,
        	keywordFilterDelEntry		INTEGER
    	}                           
    
	keywordFilterIndex	OBJECT-TYPE
				SYNTAX INTEGER
				MAX-ACCESS not-accessible
				STATUS current
				DESCRIPTION 
					"Keyword Filter Index."
				::= { keywordFilterEntry 1 }

	keywordFilterKeyword	OBJECT-TYPE
				SYNTAX OCTET STRING ( SIZE (1..32) )
				MAX-ACCESS read-write
				STATUS current
				DESCRIPTION
					"Keyword of keyword filter list."
				::= { keywordFilterEntry 2 }

	keywordFilterDelEntry	OBJECT-TYPE
				SYNTAX INTEGER { yes(1), no(2) }
				MAX-ACCESS read-write
				STATUS current
				DESCRIPTION
					"Delete the keyword filter enntry."
				::= { keywordFilterEntry 3 }

-- **********************************************************************
-- *  End of Keyword Filter Config Section 
-- **********************************************************************

-- **********************************************************************
-- *  Network Services Filter Section 
-- **********************************************************************

	network-services-filter	OBJECT IDENTIFIER ::= { firewall 4 }

	enableNetworkServicesFilter	OBJECT-TYPE
				SYNTAX INTEGER { yes(1), no(2) }
				MAX-ACCESS read-write
				STATUS current
				DESCRIPTION
					"Select [Yes] to enable filter that specify IP or port for control incoming and outgoing packets."
				::= { network-services-filter 1 }

	filterTableType		OBJECT-TYPE
				SYNTAX INTEGER { white-list(1), black-list(2) }
				MAX-ACCESS read-write
				STATUS current
				DESCRIPTION
					"Select either White List or Black List to accept or reject those LAN to WAN packet exchanges 
					for clients specified in the filter table."
				::= { network-services-filter 2 }

	weekDaysEnableLANtoWANFilter	OBJECT-TYPE
				SYNTAX BITS { monday(0), tuesday(1), wednesday(2), thursday(3), friday(4) }
				MAX-ACCESS read-write
				STATUS current
				DESCRIPTION
					"This field defines the dates that LAN to WAN filter will be enabled."
				::= { network-services-filter 3 }

	weekDaysFilterStartTimeH	OBJECT-TYPE
				SYNTAX INTEGER ( 0..23 )              
                                MAX-ACCESS read-write
				STATUS current
				DESCRIPTION
					"Hour of starting time of weekdays to enable Network Services Filter."
				::= { network-services-filter 4 }

	weekDaysFilterStartTimeM	OBJECT-TYPE
				SYNTAX INTEGER ( 0..59 )
				MAX-ACCESS read-write
				STATUS current
				DESCRIPTION
					"Minute of starting time of weekdays to enable Network Services Filter."
				::= { network-services-filter 5 }

	weekDaysFilterEndTimeH	OBJECT-TYPE
				SYNTAX INTEGER ( 0..23 )              
                                MAX-ACCESS read-write
				STATUS current
				DESCRIPTION
					"Hour of ending time of weekdays to enable Network Services Filter."
				::= { network-services-filter 6 }

	weekDaysFilterEndTimeM	OBJECT-TYPE
				SYNTAX INTEGER ( 0..59 )
				MAX-ACCESS read-write
				STATUS current
				DESCRIPTION
					"Minute of ending time of weekdays to enable Network Services Filter."
				::= { network-services-filter 7 }

	weekendEnableLANtoWANFilter	OBJECT-TYPE
				SYNTAX BITS { saturday(0), sunday(1) }
				MAX-ACCESS read-write
				STATUS current
				DESCRIPTION
					"This field defines the dates that LAN to WAN filter will be enabled."
				::= { network-services-filter 8 }

	weekendFilterStartTimeH	OBJECT-TYPE
				SYNTAX INTEGER ( 0..23 )              
                                MAX-ACCESS read-write
				STATUS current
				DESCRIPTION
					"Hour of starting time of weekend to enable Network Services Filter."
				::= { network-services-filter 9 }

	weekendFilterStartTimeM	OBJECT-TYPE
				SYNTAX INTEGER ( 0..59 )
				MAX-ACCESS read-write
				STATUS current
				DESCRIPTION
					"Minute of starting time of weekend to enable Network Services Filter."
				::= { network-services-filter 10 }

	weekendFilterEndTimeH	OBJECT-TYPE
				SYNTAX INTEGER ( 0..23 )              
                                MAX-ACCESS read-write
				STATUS current
				DESCRIPTION
					"Hour of ending time of weekend to enable Network Services Filter."
				::= { network-services-filter 11 }

	weekendFilterEndTimeM	OBJECT-TYPE
				SYNTAX INTEGER ( 0..59 )
				MAX-ACCESS read-write
				STATUS current
				DESCRIPTION
					"Minute of ending time of weekend to enable Network Services Filter."
				::= { network-services-filter 12 }

	filteredICMPPacketTypes	OBJECT-TYPE
				SYNTAX OCTET STRING ( SIZE (1..32) )
				MAX-ACCESS read-write
				STATUS current
				DESCRIPTION
					"This field defines a list of LAN to WAN ICMP packets type that will be filtered. For example, 
					if you would like to filter Echo(type 8) and Echo Reply(type 0) ICMP packets, you need to enter 
					a string with numbers separated by blank, such as, [0 8]."
				::= { network-services-filter 13 }

	networkServicesFilterTable	OBJECT-TYPE
				SYNTAX SEQUENCE OF NetworkServicesFilterEntry
				MAX-ACCESS not-accessible
				STATUS current
				DESCRIPTION
					"Network services filter list."
				::= { network-services-filter 14 }

	networkServicesFilterEntry	OBJECT-TYPE
				SYNTAX NetworkServicesFilterEntry
				MAX-ACCESS not-accessible
				STATUS current
				DESCRIPTION ""
				INDEX { networkServicesFilterIndex }
				::= { networkServicesFilterTable 1 }

 	NetworkServicesFilterEntry ::= SEQUENCE {
        	networkServicesFilterIndex			INTEGER,
		networkServicesFilterSourceIP			IpAddress,
		networkServicesFilterSourcePortRange		OCTET STRING,
		networkServicesFilterDestinationIP		IpAddress,
		networkServicesFilterDestinationPortRange	OCTET STRING,
		networkServicesFilterProtocol			INTEGER,
        	networkServicesFilterDelEntry			INTEGER
    	}                           
    
	networkServicesFilterIndex	OBJECT-TYPE
				SYNTAX INTEGER
				MAX-ACCESS not-accessible
				STATUS current
				DESCRIPTION 
					"Network Services Filter Index."
				::= { networkServicesFilterEntry 1 }

	networkServicesFilterSourceIP	OBJECT-TYPE
				SYNTAX IpAddress
				MAX-ACCESS read-write
				STATUS current
				DESCRIPTION
					"Source IP of network services filter list."
				::= { networkServicesFilterEntry 2 }

	networkServicesFilterSourcePortRange	OBJECT-TYPE
				SYNTAX OCTET STRING ( SIZE (1..11) )
				MAX-ACCESS read-write
				STATUS current
				DESCRIPTION
					"Source port range of network services filter list."
				::= { networkServicesFilterEntry 3 }

	networkServicesFilterDestinationIP	OBJECT-TYPE
				SYNTAX IpAddress
				MAX-ACCESS read-write
				STATUS current
				DESCRIPTION
					"Destination IP of network services filter list."
				::= { networkServicesFilterEntry 4 }

	networkServicesFilterDestinationPortRange	OBJECT-TYPE
				SYNTAX OCTET STRING ( SIZE (1..11) )
				MAX-ACCESS read-write
				STATUS current
				DESCRIPTION
					"Destination port range of network services filter list."
				::= { networkServicesFilterEntry 5 }

	networkServicesFilterProtocol	OBJECT-TYPE
				SYNTAX INTEGER { tcp(1), tcp-all(2), tcp-syn(3), tcp-ack(4), tcp-fin(5), tcp-rst(6), tcp-urg(7), tcp-psh(8), udp(9) }
				MAX-ACCESS read-write
				STATUS current
				DESCRIPTION
					"Destination port range of network services filter list."
				::= { networkServicesFilterEntry 6 }

	networkServicesFilterDelEntry	OBJECT-TYPE
				SYNTAX INTEGER { yes(1), no(2) }
				MAX-ACCESS read-write
				STATUS current
				DESCRIPTION
					"Delete the network services filter enntry."
				::= { networkServicesFilterEntry 7 }

-- **********************************************************************
-- *  End of Network Services Filter Config Section 
-- **********************************************************************

-- ======================================================================
-- * End of Firewall Section
-- ======================================================================





-- ======================================================================
-- * Administration Section
-- ======================================================================

-- **********************************************************************
-- *  Operation Mode Section 
-- **********************************************************************

	operation-mode		OBJECT IDENTIFIER ::= { administration 1 }

	operationMode		OBJECT-TYPE
				SYNTAX INTEGER { wireless-router-mode(1), access-point-mode(2), repeater-mode(3) }
				MAX-ACCESS read-write
				STATUS current
				DESCRIPTION
					"RT-N12 supports several operation modes to meet different requirements. Please select 
					the mode that match your situation.
					* In wireless router/ IP sharing mode, RT-N12 connects to the Internet via PPPoE, DHCP, 
					PPTP, L2TP, or Static IP and shares the wireless network to LAN clients or devices. In 						this mode, NAT, firewall, and DHCP server are enabled by default. UPnP and Dynamic DNS 
					are supported for SOHO and home users. Select this mode if you are a first-time user or 
					you are not currently using any wired/wireless routers.
					* In Access Point (AP) mode, RT-N12 connects to a wireless router through an Ethernet 
					cable to extend the wireless signal coverage to other network clients. In this mode, the 
					firewall, IP sharing, and NAT functions are disabled by default."
				::= { operation-mode 1 }

-- **********************************************************************
-- *  End of Operation Mode Config Section 
-- **********************************************************************

-- **********************************************************************
-- *  System Section 
-- **********************************************************************

	system			OBJECT IDENTIFIER ::= { administration 2 }

	login-password		OBJECT IDENTIFIER ::= { system 1 }

	routerLoginName		OBJECT-TYPE
				SYNTAX OCTET STRING ( SIZE (1..20) )
				MAX-ACCESS read-write
				STATUS current
				DESCRIPTION ""
				::= { login-password 1 }

	newPassword		OBJECT-TYPE
				SYNTAX OCTET STRING ( SIZE (1..16) )
				MAX-ACCESS read-write
				STATUS current
				DESCRIPTION
					"Password cannot be greater than 16 characters."
				::= { login-password 2 }

	miscellaneous		OBJECT IDENTIFIER ::= { system 2 }

	wpsButtonBehavior	OBJECT-TYPE
				SYNTAX INTEGER { toggle-radio(1), activate-wps(2) }
				MAX-ACCESS read-write
				STATUS current
				DESCRIPTION ""
				::= { miscellaneous 1 }

	remoteLogServer		OBJECT-TYPE
				SYNTAX IpAddress
				MAX-ACCESS read-write
				STATUS current
				DESCRIPTION
					"This field allows to assign a remote server to record log messages of RT-N12. If you 
					leave it blank, the system will record up to 1024 messages on RT-N12."
				::= { miscellaneous 2 }

	timeZone		OBJECT-TYPE
				SYNTAX INTEGER (1..85)
				MAX-ACCESS read-write
				STATUS current
				DESCRIPTION
					"
					1	(GMT-12:00) Eniwetok, Kwajalein
					2	(GMT-11:00) Midway Island, Samoa
					3	(GMT-10:00) Hawaii
					4	(GMT-09:00) Alaska
					5	(GMT-08:00) Pacific Time (US, Canada)
					6	(GMT-07:00) Mountain Time (US, Canada)
					7	(GMT-07:00) Arizona
					8	(GMT-07:00) Chihuahua, La Paz, Mazatlan
					9	(GMT-06:00) Central Time (US, Canada)
					10	(GMT-06:00) Saskatchewan
					11	(GMT-06:00) Guadalajara, Mexico City
					12	(GMT-06:00) Monterrey
					13	(GMT-06:00) Central America
					14	(GMT-05:00) Eastern Time (US, Canada)
					15	(GMT-05:00) Indiana (East)
					16	(GMT-05:00) Bogota, Lima, Quito
					17	(GMT-04:00) Atlantic Time (Canada)
					18	(GMT-04:00) Caracas, La Paz
					19	(GMT-04:00) Santiago
					20	(GMT-03:30) Newfoundland
					21	(GMT-03:00) Brasilia
					22	(GMT-03:00) Buenos Aires, Georgetown
					23	(GMT-03:00) Greenland
					24	(GMT-02:00) Mid-Atlantic
					25	(GMT-01:00) Azores
					26	(GMT-01:00) Cape Verde Is.
					27	(GMT) Greenwich Mean Time
					28	(GMT) Casablanca, Monrovia
					29	(GMT+01:00) Belgrade, Bratislava, Budapest
					30	(GMT+01:00) Ljubljana, Prague
					31	(GMT+01:00) Sarajevo, Skopje, Sofija
					32	(GMT+01:00) Vilnius, Warsaw, Zagreb
					33	(GMT+01:00) Brussels, Copenhagen
					34	(GMT+01:00) Madrid, Paris
					35	(GMT+01:00) Amsterdam, Berlin, Bern
					36	(GMT+01:00) Rome, Stockholm, Vienna
					37	(GMT+01:00) West Central Africa
					38	(GMT+02:00) Bucharest
					39	(GMT+02:00) Cairo
	 				40	(GMT+02:00) Helsinki, Riga, Tallinn
					41	(GMT+02:00) Athens, Istanbul, Minsk
	 				42	(GMT+02:00) Jerusalem
	 				43	(GMT+02:00) Harare, Pretoria
					44	(GMT+02:00) Ukraine
					45	(GMT+03:00) Kaliningrad, Kuwait, Riyadh
					46	(GMT+03:00) Nairobi
					47	(GMT+03:00) Baghdad
					48	(GMT+03:30) Tehran
					49	(GMT+04:00) Moscow, St. Petersburg
					50	(GMT+04:00) Volgograd
					51	(GMT+04:00) Abu Dhabi, Muscat
					52	(GMT+04:00) Baku, Tbilisi, Yerevan
					53	(GMT+04:30) Kabul
					54	(GMT+05:00) Islamabad, Karachi, Tashkent
					55	(GMT+05:30) Calcutta, Chennai
					56	(GMT+05:30) Mumbai, New Delhi
					57	(GMT+05:30) Sri Jayawardenepura
					58	(GMT+05:45) Kathmandu
					59	(GMT+06:00) Almaty
					60	(GMT+06:00) Yekaterinburg
					61	(GMT+06:00) Astana, Dhaka
					62	(GMT+06:30) Rangoon
					63	(GMT+07:00) Bangkok, Hanoi, Jakarta, Novosibirsk
					64	(GMT+08:00) Krasnoyarsk
					65	(GMT+08:00) Beijing, Hong Kong
					66	(GMT+08:00) Chongqing, Urumqi
					67	(GMT+08:00) Kuala Lumpur, Singapore
					68	(GMT+08:00) Taipei
					69	(GMT+08:00) Perth
					70	(GMT+08:00) Ulaan Bataar
					71	(GMT+09:00) Irkutsk, Seoul
					72	(GMT+09:00) Osaka, Sapporo, Tokyo
					73	(GMT+09:30) Darwin
					74	(GMT+09:30) Adelaide
					75	(GMT+10:00) Yakutsk
					76	(GMT+10:00) Canberra, Melbourne, Sydney
					77	(GMT+10:00) Brisbane
					78	(GMT+10:00) Hobart
					79	(GMT+10:00) Guam, Port Moresby
					80	(GMT+11:00) Vladivostok
					81	(GMT+11:00) Solomon Is.
					82	(GMT+11:00) New Caledonia
					83	(GMT+12:00) Magadan, Fiji, Kamchatka, Marshall Is.
					84	(GMT+12:00) Auckland, Wellington
					85	(GMT+13:00) Nuku'alofa
		                        "
				::= { miscellaneous 3 }

	manuallySetDaylightSaveingTime		OBJECT-TYPE
				SYNTAX INTEGER { yes(1), no(2) }
				MAX-ACCESS read-write
				STATUS current
				DESCRIPTION
					"Manually set the daylight saving time."
				::= { miscellaneous 4 }

	dstStartTimeMonth	OBJECT-TYPE
				SYNTAX INTEGER { M1(1), M2(2), M3(3), M4(4), M5(5), M6(6), M7(7), M8(8), M9(9), M10(10), M11(11), M12(12) }
                                MAX-ACCESS read-write
				STATUS current
				DESCRIPTION
					"The month of DST start time."
				::= { miscellaneous 5 }

	dstStartTimeWeek	OBJECT-TYPE
				SYNTAX INTEGER ( 1..5 )              
                                MAX-ACCESS read-write
				STATUS current
				DESCRIPTION
					"The week of DST start time."
				::= { miscellaneous 6 }

	dstStartTimeWeekday	OBJECT-TYPE
				SYNTAX INTEGER ( 0..6 )              
                                MAX-ACCESS read-write
				STATUS current
				DESCRIPTION
					"The weekday of DST start time."
				::= { miscellaneous 7 }

	dstStartTimeHour	OBJECT-TYPE
				SYNTAX INTEGER ( 0..23 )              
                                MAX-ACCESS read-write
				STATUS current
				DESCRIPTION
					"The hour of DST start time."
				::= { miscellaneous 8 }

	dstEndTimeMonth	OBJECT-TYPE
				SYNTAX INTEGER { M1(1), M2(2), M3(3), M4(4), M5(5), M6(6), M7(7), M8(8), M9(9), M10(10), M11(11), M12(12) }
                                MAX-ACCESS read-write
				STATUS current
				DESCRIPTION
					"The month of DST end time."
				::= { miscellaneous 9 }

	dstEndTimeWeek	OBJECT-TYPE
				SYNTAX INTEGER ( 1..5 )              
                                MAX-ACCESS read-write
				STATUS current
				DESCRIPTION
					"The week of DST end time."
				::= { miscellaneous 10 }

	dstEndTimeWeekday	OBJECT-TYPE
				SYNTAX INTEGER ( 0..6 )              
                                MAX-ACCESS read-write
				STATUS current
				DESCRIPTION
					"The weekday of DST end time."
				::= { miscellaneous 11 }

	dstEndTimeHour	OBJECT-TYPE
				SYNTAX INTEGER ( 0..23 )              
                                MAX-ACCESS read-write
				STATUS current
				DESCRIPTION
					"The hour of DST end time."
				::= { miscellaneous 12 }

	ntpServer		OBJECT-TYPE
				SYNTAX OCTET STRING ( SIZE (1..256) )
				MAX-ACCESS read-write
				STATUS current
				DESCRIPTION
					"To synchronize your system time with NTP Server."
				::= { miscellaneous 13 }

	enableTelnet		OBJECT-TYPE
				SYNTAX INTEGER { yes(1), no(2) }
				MAX-ACCESS read-write
				STATUS current
				DESCRIPTION ""
				::= { miscellaneous 14 }

--	authenticationMethod	OBJECT-TYPE
--				SYNTAX INTEGER { http(1), https(2), both(3) }
--				MAX-ACCESS read-write
--				STATUS current
--				DESCRIPTION ""
--				::= { miscellaneous 15 }

--	httpsLanPort		OBJECT-TYPE
--				SYNTAX INTEGER
--				MAX-ACCESS read-write
--				STATUS current
--				DESCRIPTION ""
--				::= { miscellaneous 16 }

	enableWebAccessfromWAN	OBJECT-TYPE
				SYNTAX INTEGER { yes(1), no(2) }
				MAX-ACCESS read-write
				STATUS current
				DESCRIPTION
					"This feature allows you to configure the wireless router via the Internet. The default 
					port is 8080 and you can use http://[WAN IP]:8080 or http://[DDNS name]:8080 to launch 
					the wireless router's web user interface."
				::= { miscellaneous 17 }

	httpPort		OBJECT-TYPE
				SYNTAX INTEGER
				MAX-ACCESS read-write
				STATUS current
				DESCRIPTION ""
				::= { miscellaneous 18 }

--	httpsPort		OBJECT-TYPE
--				SYNTAX INTEGER
--				MAX-ACCESS read-write
--				STATUS current
--				DESCRIPTION ""
--				::= { miscellaneous 19 }

--	onlyAllowSpecificIP	OBJECT-TYPE
--				SYNTAX INTEGER { yes(1), no(2) }
--				MAX-ACCESS read-write
--				STATUS current
--				DESCRIPTION ""
--				::= { miscellaneous 20 }

--	mClientListAct		OBJECT-TYPE
--				SYNTAX INTEGER { scan(1), nothing(2) }
--				MAX-ACCESS read-write
--				STATUS current
--				DESCRIPTION ""
--				::= { miscellaneous 21 }

--	mClientTable		OBJECT-TYPE
--				SYNTAX SEQUENCE OF MClientEntry
--				MAX-ACCESS not-accessible
--				STATUS current
--				DESCRIPTION ""
--                              ::= { miscellaneous 22 }

--	mClientEntry		OBJECT-TYPE
--				SYNTAX MClientEntry
--				MAX-ACCESS not-accessible
--				STATUS current
--				DESCRIPTION ""
--				INDEX { mClientIndex }
--				::= { mClientTable 1 }

-- 	MClientEntry ::= SEQUENCE {
--        	mClientIndex    	INTEGER,
--        	mClientIPAddr	        IpAddress,
--        	mClientName		OCTET STRING
--    	}

--	mClientIndex		OBJECT-TYPE
--				SYNTAX INTEGER ( 1..32 )
--				MAX-ACCESS not-accessible
--				STATUS current
--				DESCRIPTION
--					"Client entry index."
--				::= { mClientEntry 1 }

--	mClientIPAddr		OBJECT-TYPE
--				SYNTAX IpAddress
--				MAX-ACCESS read-only
--				STATUS current
--				DESCRIPTION
--					"MAC address of the client list."
--				::= { mClientEntry 2 }

--	mClientName		OBJECT-TYPE
--				SYNTAX OCTET STRING
--				MAX-ACCESS read-only
--				STATUS current
--				DESCRIPTION
--					"Name of the client list."
--				::= { mClientEntry 3 }

--	httpClientListTable	OBJECT-TYPE
--				SYNTAX SEQUENCE OF HttpClientListEntry
--				MAX-ACCESS not-accessible
--				STATUS current
--				DESCRIPTION
--					"HTTP client list."
--				::= { miscellaneous 23 }

--	httpClientListEntry	OBJECT-TYPE
--				SYNTAX HttpClientListEntry
--				MAX-ACCESS not-accessible
--				STATUS current
--				DESCRIPTION ""
--				INDEX { httpClientListIndex }
--				::= { httpClientListTable 1 }

-- 	HttpClientListEntry ::= SEQUENCE {
--        	httpClientListIndex		INTEGER,
--		httpClientListClient		IpAddress,
--        	httpClientListDelEntry		INTEGER
--    	}
    
--	httpClientListIndex	OBJECT-TYPE
--				SYNTAX INTEGER
--				MAX-ACCESS not-accessible
--				STATUS current
--				DESCRIPTION 
--					"HTTP Client Index."
--				::= { httpClientListEntry 1 }

--	httpClientListClient	OBJECT-TYPE
--				SYNTAX IpAddress
--				MAX-ACCESS read-write
--				STATUS current
--				DESCRIPTION
--					"Client of http client list."
--				::= { httpClientListEntry 2 }

--	httpClientListDelEntry	OBJECT-TYPE
--				SYNTAX INTEGER { yes(1), no(2) }
--				MAX-ACCESS read-write
--				STATUS current
--				DESCRIPTION
--					"Delete the http client enntry."
--				::= { httpClientListEntry 3 }

-- **********************************************************************
-- *  End of System Config Section 
-- **********************************************************************

-- **********************************************************************
-- *  Firmware Upgrade Section 
-- **********************************************************************

	firmware-upgrade	OBJECT IDENTIFIER ::= { administration 3 }

	fTftpSrv		OBJECT-TYPE
				SYNTAX OCTET STRING ( SIZE (0..39) )
				MAX-ACCESS read-write
				STATUS current
				DESCRIPTION
					"Tftp server ip."
                                ::= { firmware-upgrade 1 }

	fTftpFile		OBJECT-TYPE
				SYNTAX OCTET STRING
				MAX-ACCESS read-write
				STATUS current
				DESCRIPTION
					"The file name of the firmware which will be uploaded to the device."
				::= { firmware-upgrade 2 }

	fFirmwareUpgrade	OBJECT-TYPE
				SYNTAX INTEGER { upgrade(1), nothing(2) }
				MAX-ACCESS read-write
				STATUS current
				DESCRIPTION
					"Upgrade firmware or not. When the firmware upgrading, please don't power off the device, 
					and wait for 80 seconds to reconnect to device."
				::= { firmware-upgrade 3 }

-- **********************************************************************
-- *  End of Firmware Upgrade Config Section 
-- **********************************************************************

-- **********************************************************************
-- *  Restore/Save/Upload Setting Section 
-- **********************************************************************

	setting-management	OBJECT IDENTIFIER ::= { administration 4 }

	sTftpSrv		OBJECT-TYPE
				SYNTAX OCTET STRING ( SIZE (0..39) )
				MAX-ACCESS read-write
				STATUS current
				DESCRIPTION
					"Tftp server ip."
				::= { setting-management 1 }

	sTftpFile		OBJECT-TYPE
				SYNTAX OCTET STRING
				MAX-ACCESS read-write
				STATUS current
				DESCRIPTION
					"The file name of the config file which will be uploaded to the device or downloaded to the 
					local PC."
				::= { setting-management 2 }

	sTftpAction		OBJECT-TYPE
				SYNTAX INTEGER { get(1), put(2), nothing(3) }
				MAX-ACCESS read-write
				STATUS current
				DESCRIPTION
					"The actions of tftp. 'Get' will get config file from remote PC to device, and 'Put' will 
					upload config file from device to remote PC."
				::= { setting-management 3 }

-- **********************************************************************
-- *  End of Restore/Save/Upload Setting Config Section 
-- **********************************************************************

-- **********************************************************************
-- *  SNMP Setup Section
-- **********************************************************************

	snmp-setup		OBJECT IDENTIFIER ::= { administration 5 } 
	
	snSystemName		OBJECT-TYPE
				SYNTAX OCTET STRING ( SIZE (0..255) )
				MAX-ACCESS read-write
				STATUS current
				DESCRIPTION
					"The value of this object is the system name of the device. This value will be seen in the 
					remote SNMP agent discovery result, and can be gotten and set by MIB browser and WEB."
				::= { snmp-setup 1 }

	snLocation		OBJECT-TYPE
				SYNTAX OCTET STRING ( SIZE (0..255) )
				MAX-ACCESS read-write
				STATUS current
				DESCRIPTION
					"The value of this object is the system location of the device. This value will be seen in 
					the remote SNMP agent discovery result, and can be gotten and set by MIB browser and WEB."
				::= { snmp-setup 2 }

	snContact		OBJECT-TYPE
				SYNTAX OCTET STRING ( SIZE (0..255) )
				MAX-ACCESS read-write
				STATUS current
				DESCRIPTION
					"The value of this object is the system contact information of the device. This value will 
					be seen in the remote SNMP agent discovery result, and can be gotten and set by MIB browser 
					and WEB."
				::= { snmp-setup 3 }	
                                
	snRWCommunity		OBJECT-TYPE
				SYNTAX OCTET STRING
				MAX-ACCESS read-write
				STATUS current
				DESCRIPTION
					"The value of this object is the read-write community used in the SNMPv1 and SNMPv2c. The 
					community string can be gotten and set by MIB browser and WEB."
				::= { snmp-setup 4 }

	snROCommunity		OBJECT-TYPE
				SYNTAX OCTET STRING
				MAX-ACCESS read-write
				STATUS current
				DESCRIPTION
					"The value of this object is the read-only community used in the SNMPv1 and SNMPv2c. The 
					community string can be gotten and set by MIB browser and WEB."
				::= { snmp-setup 5 }

	snmpV3Setting		OBJECT IDENTIFIER ::= { snmp-setup 6 }

	authProtocol		OBJECT-TYPE
				SYNTAX INTEGER { none(1), md5(2), sha(3) }
				MAX-ACCESS read-write
				STATUS current
				DESCRIPTION
					"The value of this object shows SNMPv3 authentication protocol."
				::= { snmpV3Setting 1 }

	authPass		OBJECT-TYPE
				SYNTAX OCTET STRING ( SIZE (8..64) )
				MAX-ACCESS read-write
				STATUS current
				DESCRIPTION
					"The authentication password. SNMPv3 pass phrases must be at least 8 characters long."
				::= { snmpV3Setting 2 }

	privProtocol		OBJECT-TYPE
				SYNTAX INTEGER { none(1), des(2), aes(3) }
				MAX-ACCESS read-write
				STATUS current
				DESCRIPTION
					"The value of this object shows SNMPv3 privacy protocol."
				::= { snmpV3Setting 3 }

	privPass		OBJECT-TYPE
				SYNTAX OCTET STRING ( SIZE (8..64) )
				MAX-ACCESS read-write
				STATUS current
				DESCRIPTION
					"The privacy password. SNMPv3 passphrases must be at least 8 characters long."
				::= { snmpV3Setting 4 }

	snVersion		OBJECT-TYPE
				SYNTAX OCTET STRING
				MAX-ACCESS read-only
				STATUS current
				DESCRIPTION
					"The value of this object is the MIB version device supports."
				::= { snmp-setup 7 }

-- **********************************************************************
-- *  End of SNMP Setup Section 
-- **********************************************************************

-- **********************************************************************
-- *  System Command Section
-- **********************************************************************
	systemCommand		OBJECT-TYPE
				SYNTAX INTEGER
				MAX-ACCESS read-write
				STATUS current
				DESCRIPTION
					"
					1	commit
					2	reboot
					3	factoryDefault
					4	restart_wireless
					5	restart_net_and_phy
					6	restart_net
					7	restart_wan_if
					8	restart_firewall
					9	restart_ddns
					10	restart_pppoe_relay
					11	restart_allnet
					12	restart_pptpd
					13	restart_all
					14	restart_time
					15	restart_qos
					16	restart_upnp
					17	restart_ntpc
					18	restart_snmpd
					19	wps_apply
					20	reset_wps
					21	nothing
					"                                         
                                ::= { administration 6 }   			
    			                                     
-- **********************************************************************
-- *  End of System Command Section 
-- **********************************************************************

-- ======================================================================
-- * End of Administration Section
-- ======================================================================





-- ======================================================================
-- * System Log Section
-- ======================================================================

-- **********************************************************************
-- *  General Log Section 
-- **********************************************************************

	general-log		OBJECT IDENTIFIER ::= { system-log 1 }

	systemTime		OBJECT-TYPE
				SYNTAX OCTET STRING
				MAX-ACCESS read-only
				STATUS current
				DESCRIPTION
					""
				::= { general-log 1 }

	upTime			OBJECT-TYPE
				SYNTAX TimeTicks
				MAX-ACCESS read-only
				STATUS current
				DESCRIPTION
					"The value of this oject is the elapsed time (in hundredths of a second) since system boot."
				::= { general-log 2 }

-- **********************************************************************
-- *  End of General Log Config Section 
-- **********************************************************************

-- **********************************************************************
-- * DHCP leases Section 
-- **********************************************************************

	dhcp-leases		OBJECT IDENTIFIER ::= { system-log 2 }

	dhcpLeasesTable		OBJECT-TYPE
                                SYNTAX SEQUENCE OF DhcpLeasesEntry
                                MAX-ACCESS not-accessible
                                STATUS current
                                DESCRIPTION
                                	"DHCP leases list."
                                ::= { dhcp-leases 1 }

	dhcpLeasesEntry		OBJECT-TYPE
				SYNTAX DhcpLeasesEntry
				MAX-ACCESS not-accessible
				STATUS current
				DESCRIPTION ""
				INDEX { dhcpLeasesIndex }
				::= { dhcpLeasesTable 1 }

 	DhcpLeasesEntry ::= SEQUENCE {
		dhcpLeasesIndex		INTEGER,
		dhcpLeasesExpires	OCTET STRING,
		dhcpLeasesMACAddr	OCTET STRING,
		dhcpLeasesIPAddr	OCTET STRING,
		dhcpLeasesHostName	OCTET STRING
    	}                           
    
	dhcpLeasesIndex		OBJECT-TYPE
				SYNTAX INTEGER
				MAX-ACCESS not-accessible
				STATUS current
				DESCRIPTION
					"DHCP Leases List Index."
				::= { dhcpLeasesEntry 1 }

	dhcpLeasesExpires	OBJECT-TYPE
				SYNTAX OCTET STRING
				MAX-ACCESS read-only
				STATUS current
				DESCRIPTION
					"The expires of DHCP leases list."
				::= { dhcpLeasesEntry 2 }

	dhcpLeasesMACAddr	OBJECT-TYPE
				SYNTAX OCTET STRING
				MAX-ACCESS read-only
				STATUS current
				DESCRIPTION
					"The MAC address of DHCP leases list."
				::= { dhcpLeasesEntry 3 }

	dhcpLeasesIPAddr	OBJECT-TYPE
				SYNTAX OCTET STRING
				MAX-ACCESS read-only
				STATUS current
				DESCRIPTION
					"The IP address of DHCP leases list."
				::= { dhcpLeasesEntry 4 }

	dhcpLeasesHostName	OBJECT-TYPE
				SYNTAX OCTET STRING
				MAX-ACCESS read-only
				STATUS current
				DESCRIPTION
					"The host name of DHCP leases list."
				::= { dhcpLeasesEntry 5 }

-- **********************************************************************
-- *  End of DHCP leases Config Section 
-- **********************************************************************

-- **********************************************************************
-- * Wireless Log Section 
-- **********************************************************************

	wireless-log		OBJECT IDENTIFIER ::= { system-log 3 }

	logWl2g			OBJECT IDENTIFIER ::= { wireless-log 1 }

	bssInfoWl2g		OBJECT-TYPE
				SYNTAX OCTET STRING
				MAX-ACCESS read-only
				STATUS current
				DESCRIPTION
					"The value of this object shows the bss info of the device."
                                ::= { logWl2g 1 } 

--	channelWl2g		OBJECT-TYPE
--				SYNTAX INTEGER
--				MAX-ACCESS read-only
--				STATUS current
--				DESCRIPTION
--					"The value of this oject shows the channel of the device."
--				::= { logWl2g 2 }

	wl2gStationTable	OBJECT-TYPE
				SYNTAX SEQUENCE OF Wl2gStationEntry
				MAX-ACCESS not-accessible
				STATUS current
				DESCRIPTION
					"2.4G station list."
                                ::= { logWl2g 2 }
                                    
	wl2gStationEntry	OBJECT-TYPE
				SYNTAX Wl2gStationEntry
				MAX-ACCESS not-accessible
				STATUS current
				DESCRIPTION ""
				INDEX { wl2gStationIndex }
				::= { wl2gStationTable 1 }

 	Wl2gStationEntry ::= SEQUENCE {
        	wl2gStationIndex	INTEGER,
        	wl2gStationMACAddr	OCTET STRING,
        	wl2gStationState	INTEGER
    	}                           
    
	wl2gStationIndex	OBJECT-TYPE
                                SYNTAX INTEGER ( 1..64 )
                                MAX-ACCESS not-accessible
                                STATUS current
                                DESCRIPTION 
                                	"2.4G Station List Index"
                                ::= { wl2gStationEntry 1 }

	wl2gStationMACAddr	OBJECT-TYPE
				SYNTAX OCTET STRING
				MAX-ACCESS read-only
				STATUS current
				DESCRIPTION
					"The MAC address of 2.4G station list."
                                ::= { wl2gStationEntry  2 } 	
                                
	wl2gStationState	OBJECT-TYPE
				SYNTAX INTEGER { associated(1), authorized(2), associated-authorized(3), none(4) }
				MAX-ACCESS read-only
				STATUS current
				DESCRIPTION
					"The state of 2.4G station list."
				::= { wl2gStationEntry 3 }

-- **********************************************************************
-- *  End of Wireless Log Config Section 
-- **********************************************************************

-- **********************************************************************
-- * Port Forwarding Section 
-- **********************************************************************

	port-forwarding-log	OBJECT IDENTIFIER ::= { system-log 4 }

	portForwardingLogTable	OBJECT-TYPE
                                SYNTAX SEQUENCE OF PortForwardingLogEntry
                                MAX-ACCESS not-accessible
                                STATUS current
                                DESCRIPTION
                                	"Port forwarding list."
                                ::= { port-forwarding-log 1 }

	portForwardingLogEntry	OBJECT-TYPE
				SYNTAX RoutingEntry
				MAX-ACCESS not-accessible
				STATUS current
				DESCRIPTION ""
				INDEX { portForwardingLogIndex }
				::= { portForwardingLogTable 1 }

 	PortForwardingLogEntry ::= SEQUENCE {
		portForwardingLogIndex		INTEGER,
		portForwardingLogDestination	OCTET STRING,
		portForwardingLogProtocol	OCTET STRING,
		portForwardingLogPortRange	OCTET STRING,
		portForwardingLogRedirectTo	OCTET STRING,
		portForwardingLogLocalPort	OCTET STRING
    	}
    
	portForwardingLogIndex	OBJECT-TYPE
				SYNTAX INTEGER
				MAX-ACCESS not-accessible
				STATUS current
				DESCRIPTION
					"Port Forwarding List Index."
				::= { portForwardingLogEntry 1 }

	portForwardingLogDestination	OBJECT-TYPE
				SYNTAX OCTET STRING
				MAX-ACCESS read-only
				STATUS current
				DESCRIPTION
					"The destination of port forwarding list."
				::= { portForwardingLogEntry 2 }

	portForwardingLogProtocol		OBJECT-TYPE
				SYNTAX OCTET STRING
				MAX-ACCESS read-only
				STATUS current
				DESCRIPTION
					"The protocol of port forwarding list."
				::= { portForwardingLogEntry 3 }

	portForwardingLogPortRange		OBJECT-TYPE
				SYNTAX OCTET STRING
				MAX-ACCESS read-only
				STATUS current
				DESCRIPTION
					"The port range of port forwarding list."
				::= { portForwardingLogEntry 4 }

	portForwardingLogRedirectTo		OBJECT-TYPE
				SYNTAX OCTET STRING
				MAX-ACCESS read-only
				STATUS current
				DESCRIPTION
					"The redirect of port forwarding list."
				::= { portForwardingLogEntry 5 }

	portForwardingLogLocalPort		OBJECT-TYPE
				SYNTAX OCTET STRING
				MAX-ACCESS read-only
				STATUS current
				DESCRIPTION
					"The local port of port forwarding list."
				::= { portForwardingLogEntry 6 }

-- **********************************************************************
-- *  End of Port Forwarding Section 
-- **********************************************************************

-- **********************************************************************
-- * Routing Table Section 
-- **********************************************************************

	routing-table		OBJECT IDENTIFIER ::= { system-log 5 }

	routingTable		OBJECT-TYPE
                                SYNTAX SEQUENCE OF RoutingEntry
                                MAX-ACCESS not-accessible
                                STATUS current
                                DESCRIPTION
                                	"Routing list."
                                ::= { routing-table 1 }

	routingEntry		OBJECT-TYPE
				SYNTAX RoutingEntry
				MAX-ACCESS not-accessible
				STATUS current
				DESCRIPTION ""
				INDEX { routingIndex }
				::= { routingTable 1 }

 	RoutingEntry ::= SEQUENCE {
		routingIndex		INTEGER,
		routingDestination	OCTET STRING,
		routingGateway		OCTET STRING,
		routingGenmask		OCTET STRING,
		routingFlags		OCTET STRING,
		routingMetric		OCTET STRING,
		routingRef		OCTET STRING,
		routingUse		OCTET STRING,
		routingIface		OCTET STRING
    	}                           
    
	routingIndex		OBJECT-TYPE
				SYNTAX INTEGER
				MAX-ACCESS not-accessible
				STATUS current
				DESCRIPTION
					"Routing List Index."
				::= { routingEntry 1 }

	routingDestination	OBJECT-TYPE
				SYNTAX OCTET STRING
				MAX-ACCESS read-only
				STATUS current
				DESCRIPTION
					"The destination of routing list."
				::= { routingEntry 2 }

	routingGateway		OBJECT-TYPE
				SYNTAX OCTET STRING
				MAX-ACCESS read-only
				STATUS current
				DESCRIPTION
					"The gateway of routing list."
				::= { routingEntry 3 }

	routingGenmask		OBJECT-TYPE
				SYNTAX OCTET STRING
				MAX-ACCESS read-only
				STATUS current
				DESCRIPTION
					"The genmask of routing list."
				::= { routingEntry 4 }

	routingFlags		OBJECT-TYPE
				SYNTAX OCTET STRING
				MAX-ACCESS read-only
				STATUS current
				DESCRIPTION
					"The flags of routing list."
				::= { routingEntry 5 }

	routingMetric		OBJECT-TYPE
				SYNTAX INTEGER
				MAX-ACCESS read-only
				STATUS current
				DESCRIPTION
					"The metric of routing list."
				::= { routingEntry 6 }

	routingRef		OBJECT-TYPE
				SYNTAX INTEGER
				MAX-ACCESS read-only
				STATUS current
				DESCRIPTION
					"The ref of routing list."
				::= { routingEntry 7 }

	routingUse		OBJECT-TYPE
				SYNTAX OCTET STRING
				MAX-ACCESS read-only
				STATUS current
				DESCRIPTION
					"The use of routing list."
				::= { routingEntry 8 }

	routingIface		OBJECT-TYPE
				SYNTAX OCTET STRING
				MAX-ACCESS read-only
				STATUS current
				DESCRIPTION
					"The Iface of routing list."
				::= { routingEntry 9 }

-- **********************************************************************
-- *  End of Routing Table Section 
-- **********************************************************************

-- ======================================================================
-- * End of System Log Section
-- ======================================================================





-- ======================================================================
-- * Guest Network Section
-- ======================================================================

-- **********************************************************************
-- *  Guest Network Section 
-- **********************************************************************

-- ++++++++++++++++++++++++++++++++++++++++++++++++++++++++++++++++++++++
-- +  Guest Network Section (2.4G)
-- ++++++++++++++++++++++++++++++++++++++++++++++++++++++++++++++++++++++

	guest-network-wl2g	OBJECT IDENTIFIER ::= { guest-network 1 }

	wl2gGuestNetworkTable	OBJECT-TYPE
                                SYNTAX SEQUENCE OF RoutingEntry
                                MAX-ACCESS not-accessible
                                STATUS current
                                DESCRIPTION
                                	"Guest network list for 2G."
                                ::= { guest-network-wl2g 1 }

	wl2gGuestNetworkEntry	OBJECT-TYPE
				SYNTAX Wl2gGuestNetworkEntry
				MAX-ACCESS not-accessible
				STATUS current
				DESCRIPTION ""
				INDEX { gIndexWl2g }
				::= { wl2gGuestNetworkTable 1 }

 	Wl2gGuestNetworkEntry ::= SEQUENCE {
		gIndexWl2g		INTEGER,
		gEnableWl2g		INTEGER,
		gSSIDWl2g		OCTET STRING,
		gAuthenticationWl2g	INTEGER,
		gWepEncryptionWl2g	INTEGER,
		gKeyIndexWl2g		INTEGER,
		gPassphraseWl2g		OCTET STRING,
		gWpaEncryptionWl2g	INTEGER,
		gWpaPreSharedKeyWl2g	OCTET STRING,
		gAccessTimeWl2g		INTEGER,
		gAccessTimeHWl2g	INTEGER,
		gAccessTimeMWl2g	INTEGER,
		gAccessIntranetWl2g	INTEGER
		
    	}
    
	gIndexWl2g		OBJECT-TYPE
				SYNTAX INTEGER ( 1..3 )
				MAX-ACCESS not-accessible
				STATUS current
				DESCRIPTION
					"Guest Network List Index for 2G."
				::= { wl2gGuestNetworkEntry 1 }

	gEnableWl2g		OBJECT-TYPE
				SYNTAX INTEGER { enable(1), disable(2) }
				MAX-ACCESS read-write
				STATUS current
				DESCRIPTION
					"The enable of guest network list for 2G."
				::= { wl2gGuestNetworkEntry 2 }

	gSSIDWl2g		OBJECT-TYPE
				SYNTAX OCTET STRING ( SIZE (1..32) )
				MAX-ACCESS read-write
				STATUS current
				DESCRIPTION
					"The SSID of guest network list for 2G."
				::= { wl2gGuestNetworkEntry 3 }

	gAuthenticationWl2g	OBJECT-TYPE                              
                                SYNTAX INTEGER { opensystem(1), sharedkey(2), wpa-personal(3), wpa2-personal(4), wpa-auto-personal(5) }
				MAX-ACCESS read-write
				STATUS current
				DESCRIPTION
					"The authentication of guest network list for 2G."
				::= { wl2gGuestNetworkEntry 4 }

	gWepEncryptionWl2g	OBJECT-TYPE
				SYNTAX INTEGER { none(1), wep-64bits(2), wep-128bits(3) }
				MAX-ACCESS read-write
				STATUS current
				DESCRIPTION 
					"The wep encryption of guest network list for 2G."
				::= { wl2gGuestNetworkEntry 5 }

	gKeyIndexWl2g		OBJECT-TYPE
				SYNTAX INTEGER { first(1), second(2), third(3), forth(4) }
				MAX-ACCESS read-write                      
                                STATUS current
				DESCRIPTION
					"The key index of guest network list for 2G."
				::= { wl2gGuestNetworkEntry 6 } 

	gPassphraseWl2g		OBJECT-TYPE
                                SYNTAX OCTET STRING
                                MAX-ACCESS read-write
                                STATUS current
				DESCRIPTION
					"The passphrase of guest network list for 2G."
				::= { wl2gGuestNetworkEntry 7 } 

	gWpaEncryptionWl2g	OBJECT-TYPE
				SYNTAX INTEGER { tkip(1), aes(2), tkip-aes(3) }
				MAX-ACCESS read-write
				STATUS current
				DESCRIPTION
					"The WPA encryption of guest network list for 2G."   
                                ::= { wl2gGuestNetworkEntry 8 }

	gWpaPreSharedKeyWl2g	OBJECT-TYPE
                                SYNTAX OCTET STRING
                                MAX-ACCESS read-write
                                STATUS current
				DESCRIPTION
					"The WPA pre-shared key of guest network list for 2G."
				::= { wl2gGuestNetworkEntry 9 }

	gAccessTimeWl2g		OBJECT-TYPE
				SYNTAX INTEGER { specific-time(1), limitless(2) }
				MAX-ACCESS read-write
				STATUS current
				DESCRIPTION
					"The access time of guest network list for 2G."
				::= { wl2gGuestNetworkEntry 10 }

	gAccessTimeHWl2g	OBJECT-TYPE
				SYNTAX INTEGER ( 0..23 )
				MAX-ACCESS read-write
				STATUS current
				DESCRIPTION
					"The access time (hour) of guest network list for 2G."
				::= { wl2gGuestNetworkEntry 11 }

	gAccessTimeMWl2g	OBJECT-TYPE
				SYNTAX INTEGER ( 0..59 )
				MAX-ACCESS read-write
				STATUS current
				DESCRIPTION
					"The access time (minute) of guest network list for 2G."
				::= { wl2gGuestNetworkEntry 12 }

	gAccessIntranetWl2g	OBJECT-TYPE
				SYNTAX INTEGER { enable(1), disable(2) }
				MAX-ACCESS read-write
				STATUS current
				DESCRIPTION
					"The access intranet of guest network list for 2G."
				::= { wl2gGuestNetworkEntry 13 }

	gSSIDWepKeyWl2g		OBJECT IDENTIFIER ::= { guest-network-wl2g 2 }
    
	gWl2gSSID1WepKeyTable	OBJECT-TYPE
				SYNTAX SEQUENCE OF GWepKeyEntry1Wl2g
				MAX-ACCESS not-accessible
				STATUS current
				DESCRIPTION
					"Wep key table of guest network 1 for 2G."
				::= { gSSIDWepKeyWl2g 1 }
      
	gWepKeyEntry1Wl2g	OBJECT-TYPE
				SYNTAX GWepKeyEntry1Wl2g
				MAX-ACCESS not-accessible
				STATUS current
				DESCRIPTION ""
				INDEX {gWepKeyIndex1Wl2g }
				::= { gWl2gSSID1WepKeyTable 1 }

	GWepKeyEntry1Wl2g ::= SEQUENCE {
        	gWepKeyIndex1Wl2g      	INTEGER,
        	gWepKeyValue1Wl2g	OCTET STRING
	}                                    

	gWepKeyIndex1Wl2g	OBJECT-TYPE
				SYNTAX INTEGER ( 1..4 )
				MAX-ACCESS not-accessible
				STATUS current
				DESCRIPTION
					"Wep key index of guest network 1 for 2G."
				::= { gWepKeyEntry1Wl2g 1 }

	gWepKeyValue1Wl2g	OBJECT-TYPE
				SYNTAX OCTET STRING
				MAX-ACCESS read-write
				STATUS current
				DESCRIPTION
					"WEP key value of guest network 1 for 2G."
				::= { gWepKeyEntry1Wl2g 2 }

	gWl2gSSID2WepKeyTable	OBJECT-TYPE
				SYNTAX SEQUENCE OF GWepKeyEntry2Wl2g
				MAX-ACCESS not-accessible
				STATUS current
				DESCRIPTION
					"Wep key table of guest network 2 for 2G."
				::= { gSSIDWepKeyWl2g 2 }
      
	gWepKeyEntry2Wl2g	OBJECT-TYPE
				SYNTAX GWepKeyEntry2Wl2g
				MAX-ACCESS not-accessible
				STATUS current
				DESCRIPTION ""
				INDEX {gWepKeyIndex2Wl2g }
				::= { gWl2gSSID2WepKeyTable 1 }

	GWepKeyEntry2Wl2g ::= SEQUENCE {
        	gWepKeyIndex2Wl2g      	INTEGER,
        	gWepKeyValue2Wl2g	OCTET STRING
	}                                    

	gWepKeyIndex2Wl2g	OBJECT-TYPE
				SYNTAX INTEGER ( 1..4 )
				MAX-ACCESS not-accessible
				STATUS current
				DESCRIPTION
					"Wep key index of guest network 2 for 2G."
				::= { gWepKeyEntry2Wl2g 1 }

	gWepKeyValue2Wl2g	OBJECT-TYPE
				SYNTAX OCTET STRING
				MAX-ACCESS read-write
				STATUS current
				DESCRIPTION
					"WEP key value of guest network 2 for 2G."
				::= { gWepKeyEntry2Wl2g 2 }


	gWl2gSSID3WepKeyTable	OBJECT-TYPE
				SYNTAX SEQUENCE OF GWepKeyEntry3Wl2g
				MAX-ACCESS not-accessible
				STATUS current
				DESCRIPTION
					"Wep key table of guest network 3 for 2G."
				::= { gSSIDWepKeyWl2g 3 }
      
	gWepKeyEntry3Wl2g	OBJECT-TYPE
				SYNTAX GWepKeyEntry3Wl2g
				MAX-ACCESS not-accessible
				STATUS current
				DESCRIPTION ""
				INDEX {gWepKeyIndex3Wl2g }
				::= { gWl2gSSID3WepKeyTable 1 }

	GWepKeyEntry3Wl2g ::= SEQUENCE {
        	gWepKeyIndex3Wl2g      	INTEGER,
        	gWepKeyValue3Wl2g	OCTET STRING
	}                                    

	gWepKeyIndex3Wl2g	OBJECT-TYPE
				SYNTAX INTEGER ( 1..4 )
				MAX-ACCESS not-accessible
				STATUS current
				DESCRIPTION
					"Wep key index of guest network 3 for 2G."
				::= { gWepKeyEntry3Wl2g 1 }

	gWepKeyValue3Wl2g	OBJECT-TYPE
				SYNTAX OCTET STRING
				MAX-ACCESS read-write
				STATUS current
				DESCRIPTION
					"WEP key value of guest network 3 for 2G."
				::= { gWepKeyEntry3Wl2g 2 }

-- ++++++++++++++++++++++++++++++++++++++++++++++++++++++++++++++++++++++
-- *  End of Guest Network Section (2.4G)
-- ++++++++++++++++++++++++++++++++++++++++++++++++++++++++++++++++++++++

-- **********************************************************************
-- *  End of Guest Network Section 
-- **********************************************************************

-- ======================================================================
-- * End of Guest Network Section
-- ======================================================================





-- ======================================================================
-- * Traffic Manager Section
-- ======================================================================

-- **********************************************************************
-- *  QoS Section 
-- **********************************************************************

-- ++++++++++++++++++++++++++++++++++++++++++++++++++++++++++++++++++++++
-- *  Automatic Mode Section 
-- ++++++++++++++++++++++++++++++++++++++++++++++++++++++++++++++++++++++

	automatic-mode		OBJECT IDENTIFIER ::= { traffic-manager 1 }

	enableQoS		OBJECT-TYPE
                                SYNTAX INTEGER { enable(1), disable(2) }
				MAX-ACCESS read-write
				STATUS current                                                        
                                DESCRIPTION ""
				::= { automatic-mode 1 }

	uploadBandwidth		OBJECT-TYPE
                                SYNTAX INTEGER
				MAX-ACCESS read-write
				STATUS current                                                        
                                DESCRIPTION
					"If the measured uplink speed is incorrect, you can assign it manually here."
				::= { automatic-mode 2 }

--	uploadScale		OBJECT-TYPE
--                                SYNTAX INTEGER { Kbs(1), Mbs(2) }
--				MAX-ACCESS read-write
--				STATUS current                                                        
--                                DESCRIPTION ""
--				::= { automatic-mode 3 }

	downloadBandwidth	OBJECT-TYPE
                                SYNTAX INTEGER
				MAX-ACCESS read-write
				STATUS current                                                        
                                DESCRIPTION
					"If the measured downlink speed is incorrect, you can assign it manually here."
				::= { automatic-mode 3 }

--	downloadScale		OBJECT-TYPE
--                                SYNTAX INTEGER { Kbs(1), Mbs(2) }
--				MAX-ACCESS read-write
--				STATUS current                                                        
--                                DESCRIPTION ""
--				::= { automatic-mode 5 }

-- ++++++++++++++++++++++++++++++++++++++++++++++++++++++++++++++++++++++
-- *  End of Automatic Mode Section 
-- ++++++++++++++++++++++++++++++++++++++++++++++++++++++++++++++++++++++

-- ++++++++++++++++++++++++++++++++++++++++++++++++++++++++++++++++++++++
-- *  User Defined Priority Section 
-- ++++++++++++++++++++++++++++++++++++++++++++++++++++++++++++++++++++++

	user-defined-priority	OBJECT IDENTIFIER ::= { traffic-manager 2 }

	uploadPriority		OBJECT IDENTIFIER ::= { user-defined-priority 1 }
	
	highestMinPriorityUp	OBJECT-TYPE
                                SYNTAX INTEGER ( 0..100 )
                                MAX-ACCESS read-write
                                STATUS current
                                DESCRIPTION
                                	"Highest priority of minimum reserved bandwidth for upload."
                                ::= { uploadPriority 1 }

	highestMaxPriorityUp	OBJECT-TYPE
                                SYNTAX INTEGER ( 0..100 )
                                MAX-ACCESS read-write
                                STATUS current
                                DESCRIPTION
                                	"Highest priority of minimum reserved bandwidth for upload."
                                ::= { uploadPriority 2 }

	highMinPriorityUp	OBJECT-TYPE
                                SYNTAX INTEGER ( 0..100 )
                                MAX-ACCESS read-write
                                STATUS current
                                DESCRIPTION
                                	"High priority of minimum reserved bandwidth for upload."
                                ::= { uploadPriority 3 }

	highMaxPriorityUp	OBJECT-TYPE
                                SYNTAX INTEGER ( 0..100 )
                                MAX-ACCESS read-write
                                STATUS current
                                DESCRIPTION
                                	"High priority of minimum reserved bandwidth for upload."
                                ::= { uploadPriority 4 }

	mediumMinPriorityUp	OBJECT-TYPE
                                SYNTAX INTEGER ( 0..100 )
                                MAX-ACCESS read-write
                                STATUS current
                                DESCRIPTION
                                	"Medium priority of minimum reserved bandwidth for upload."
                                ::= { uploadPriority 5 }

	mediumMaxPriorityUp	OBJECT-TYPE
                                SYNTAX INTEGER ( 0..100 )
                                MAX-ACCESS read-write
                                STATUS current
                                DESCRIPTION
                                	"Medium priority of minimum reserved bandwidth for upload."
                                ::= { uploadPriority 6 }

	lowMinPriorityUp	OBJECT-TYPE
                                SYNTAX INTEGER ( 0..100 )
                                MAX-ACCESS read-write
                                STATUS current
                                DESCRIPTION
                                	"Low priority of minimum reserved bandwidth for upload."
                                ::= { uploadPriority 7 }

	lowMaxPriorityUp	OBJECT-TYPE
                                SYNTAX INTEGER ( 0..100 )
                                MAX-ACCESS read-write
                                STATUS current
                                DESCRIPTION
                                	"Low priority of minimum reserved bandwidth for upload."
                                ::= { uploadPriority 8 }

	lowestMinPriorityUp	OBJECT-TYPE
                                SYNTAX INTEGER ( 0..100 )
                                MAX-ACCESS read-write
                                STATUS current
                                DESCRIPTION
                                	"Lowest priority of minimum reserved bandwidth for upload."
                                ::= { uploadPriority 9 }

	lowestMaxPriorityUp	OBJECT-TYPE
                                SYNTAX INTEGER ( 0..100 )
                                MAX-ACCESS read-write
                                STATUS current
                                DESCRIPTION
                                	"Lowest priority of minimum reserved bandwidth for upload."
                                ::= { uploadPriority 10 }

	downloadPriority	OBJECT IDENTIFIER ::= { user-defined-priority 2 }

	highestMaxPriorityDown	OBJECT-TYPE
                                SYNTAX INTEGER ( 0..100 )
                                MAX-ACCESS read-write
                                STATUS current
                                DESCRIPTION
                                	"Highest priority of minimum reserved bandwidth for download."
                                ::= { downloadPriority 1 }

	highMaxPriorityDown	OBJECT-TYPE
                                SYNTAX INTEGER ( 0..100 )
                                MAX-ACCESS read-write
                                STATUS current
                                DESCRIPTION
                                	"High priority of minimum reserved bandwidth for download."
                                ::= { downloadPriority 2 }

	mediumMaxPriorityDown	OBJECT-TYPE
                                SYNTAX INTEGER ( 0..100 )
                                MAX-ACCESS read-write
                                STATUS current
                                DESCRIPTION
                                	"Medium priority of minimum reserved bandwidth for download."
                                ::= { downloadPriority 3 }

	lowMaxPriorityDown	OBJECT-TYPE
                                SYNTAX INTEGER ( 0..100 )
                                MAX-ACCESS read-write
                                STATUS current
                                DESCRIPTION
                                	"Low priority of minimum reserved bandwidth for download."
                                ::= { downloadPriority 4 }

	lowestMaxPriorityDown	OBJECT-TYPE
                                SYNTAX INTEGER ( 0..100 )
                                MAX-ACCESS read-write
                                STATUS current
                                DESCRIPTION
                                	"Lowest priority of minimum reserved bandwidth for download."
                                ::= { downloadPriority 5 }

	highestPriorityPacket	OBJECT-TYPE
				SYNTAX BITS { ack(0), syn(1), fin(2), rst(3), icmp(4) }
				MAX-ACCESS read-write
				STATUS current
				DESCRIPTION ""
				::= { user-defined-priority 3 }

-- ++++++++++++++++++++++++++++++++++++++++++++++++++++++++++++++++++++++
-- *  End of User Defined Priority Section
-- ++++++++++++++++++++++++++++++++++++++++++++++++++++++++++++++++++++++

-- ++++++++++++++++++++++++++++++++++++++++++++++++++++++++++++++++++++++
-- *  User Defined QoS rules Section
-- ++++++++++++++++++++++++++++++++++++++++++++++++++++++++++++++++++++++

	user-defined-qos-rules	OBJECT IDENTIFIER ::= { traffic-manager 3 }

	userSpecifyRuleTable	OBJECT-TYPE
				SYNTAX SEQUENCE OF UserSpecifyRuleEntry
				MAX-ACCESS not-accessible
				STATUS current
				DESCRIPTION
					"User specify rule list."
				::= { user-defined-qos-rules 1 }

	userSpecifyRuleEntry	OBJECT-TYPE
				SYNTAX UserSpecifyRuleEntry
				MAX-ACCESS not-accessible
				STATUS current
				DESCRIPTION ""
				INDEX { userSpecifyRuleIndex }
				::= { userSpecifyRuleTable 1 }

 	UserSpecifyRuleEntry ::= SEQUENCE {
        	userSpecifyRuleIndex		INTEGER,
        	userSpecifyRuleServiceName	OCTET STRING,
		userSpecifyRuleSrcIPorMAC	OCTET STRING,
		userSpecifyRuleDestPort		OCTET STRING,
		userSpecifyRuleProtocol		INTEGER,
		userSpecifyRuleMinTransferred	INTEGER,
		userSpecifyRuleMaxTransferred	INTEGER,
		userSpecifyRulePriority		INTEGER,
        	userSpecifyRuleDelEntry		INTEGER
    	}                           
    
	userSpecifyRuleIndex	OBJECT-TYPE
				SYNTAX INTEGER
				MAX-ACCESS not-accessible
				STATUS current
				DESCRIPTION 
					"User Specify Rule Index."
				::= { userSpecifyRuleEntry 1 }

	userSpecifyRuleServiceName	OBJECT-TYPE
				SYNTAX OCTET STRING
				MAX-ACCESS read-write
				STATUS current
				DESCRIPTION
					"Service name of user specify rule list."
				::= { userSpecifyRuleEntry 2 }

	userSpecifyRuleSrcIPorMAC	OBJECT-TYPE
				SYNTAX OCTET STRING
				MAX-ACCESS read-write
				STATUS current
				DESCRIPTION
					"IP or MAC of user specify rule list."
				::= { userSpecifyRuleEntry 3 }

	userSpecifyRuleDestPort	OBJECT-TYPE
				SYNTAX OCTET STRING
				MAX-ACCESS read-write
				STATUS current
				DESCRIPTION
					"Destination port of user specify rule list."
				::= { userSpecifyRuleEntry 4 }

	userSpecifyRuleProtocol	OBJECT-TYPE
				SYNTAX INTEGER { tcp(1), udp(2), tcp-or-udp(3), any(4) }
				MAX-ACCESS read-write
				STATUS current
				DESCRIPTION
					"Protocol of user specify rule list."
				::= { userSpecifyRuleEntry 5 }

	userSpecifyRuleMinTransferred	OBJECT-TYPE
				SYNTAX INTEGER
				MAX-ACCESS read-write
				STATUS current
				DESCRIPTION
					"Minimum transferred of user specify rule list."
				::= { userSpecifyRuleEntry 6 }
	
	userSpecifyRuleMaxTransferred	OBJECT-TYPE
				SYNTAX INTEGER
				MAX-ACCESS read-write
				STATUS current
				DESCRIPTION
					"Maxmum transferred of user specify rule list."
				::= { userSpecifyRuleEntry 7 }

	userSpecifyRulePriority	OBJECT-TYPE
				SYNTAX INTEGER { highest(1), high(2), medium(3), low(4), lowest(5) }
				MAX-ACCESS read-write
				STATUS current
				DESCRIPTION
					"Priority of user specify rule list."
				::= { userSpecifyRuleEntry 8 }

	userSpecifyRuleDelEntry	OBJECT-TYPE
				SYNTAX INTEGER { yes(1), no(2) }
				MAX-ACCESS read-write
				STATUS current
				DESCRIPTION
					"Delete the user specify rule enntry."
				::= { userSpecifyRuleEntry 9 }

-- **********************************************************************
-- *  End of User Defined QoS rules Section
-- **********************************************************************

-- **********************************************************************
-- *  End of QoS Section 
-- **********************************************************************

-- ======================================================================
-- * End of Traffic Manager Section
-- ======================================================================





-- ======================================================================
-- * Quick Internet Setup Section
-- ======================================================================

-- **********************************************************************
-- *  Internet Setup Section 
-- **********************************************************************

-- ++++++++++++++++++++++++++++++++++++++++++++++++++++++++++++++++++++++
-- *  Lan IP Setting Section
-- ++++++++++++++++++++++++++++++++++++++++++++++++++++++++++++++++++++++

	internet-setup		OBJECT IDENTIFIER ::= { quick-internet-setup 1 }

	lan-ip-setting		OBJECT IDENTIFIER ::= { internet-setup 1 }

	qGetIpAutomatically	OBJECT-TYPE
				SYNTAX INTEGER { yes(1), no(2) }
				MAX-ACCESS read-write
				STATUS current
				DESCRIPTION ""
                                ::= { lan-ip-setting 1 }
	
	qIPAddress		OBJECT-TYPE
				SYNTAX IpAddress
				MAX-ACCESS read-write
				STATUS current
				DESCRIPTION
		                        "The value of this object is IP Address of the device as seen in your local network. 
					The default value is 192.168.1.1."
                                ::= { lan-ip-setting 2 }

	qSubnetMask		OBJECT-TYPE
				SYNTAX IpAddress
				MAX-ACCESS read-write
				STATUS current
				DESCRIPTION
					"The value this object is Subnet Mask of the device as seen in your local network. 
					The default value is 255.255.255.0."
				::= { lan-ip-setting 3 }

	qDefaultGateway		OBJECT-TYPE
				SYNTAX IpAddress
				MAX-ACCESS read-write
				STATUS current
				DESCRIPTION ""
				::= { lan-ip-setting 4 }

	qConnectToDnsServerAutomatically	OBJECT-TYPE
				SYNTAX INTEGER { yes(1), no(2) }
				MAX-ACCESS read-write
				STATUS current
				DESCRIPTION ""
                                ::= { lan-ip-setting 5 }

	qDnsServer1		OBJECT-TYPE
				SYNTAX IpAddress
				MAX-ACCESS read-write
				STATUS current
				DESCRIPTION ""
				::= { lan-ip-setting 6 }

	qDnsServer2		OBJECT-TYPE
				SYNTAX IpAddress
				MAX-ACCESS read-write
				STATUS current
				DESCRIPTION ""
				::= { lan-ip-setting 7 }

-- ++++++++++++++++++++++++++++++++++++++++++++++++++++++++++++++++++++++
-- *  End of Lan IP Setting Section
-- ++++++++++++++++++++++++++++++++++++++++++++++++++++++++++++++++++++++

-- ++++++++++++++++++++++++++++++++++++++++++++++++++++++++++++++++++++++
-- *  AP Connection Section
-- ++++++++++++++++++++++++++++++++++++++++++++++++++++++++++++++++++++++

	ap-connection		OBJECT IDENTIFIER ::= { internet-setup 2 }
	
	qAPScanAct		OBJECT-TYPE
				SYNTAX INTEGER { scan(1), nothing(2) }
				MAX-ACCESS read-write
				STATUS current
				DESCRIPTION ""
				::= { ap-connection 1 }

	qAPScanTable		OBJECT-TYPE
				SYNTAX SEQUENCE OF QAPScanEntry
				MAX-ACCESS not-accessible
				STATUS current
				DESCRIPTION ""
                                ::= { ap-connection 2 }

	qAPScanEntry		OBJECT-TYPE
				SYNTAX QAPScanEntry
				MAX-ACCESS not-accessible
				STATUS current
				DESCRIPTION ""
				INDEX { qAPResultIndex }
				::= { qAPScanTable 1 }

 	QAPScanEntry ::= SEQUENCE {
        	qAPResultIndex 		INTEGER,
		qAPResultBand	        OCTET STRING,
        	qAPResultSSID		OCTET STRING,
		qAPResultChannel	INTEGER,
		qAPResultAuthentication	INTEGER,
		qAPResultEncryption	INTEGER,
		qAPResultRssi		INTEGER,
		qAPResultBSSID	        OCTET STRING,
		qAPResultMode		INTEGER,
		qAPResultStatus		INTEGER
    	}

	qAPResultIndex		OBJECT-TYPE
				SYNTAX INTEGER ( 1..32 )
				MAX-ACCESS not-accessible
				STATUS current
				DESCRIPTION
					"AP scan result entry index."
				::= { qAPScanEntry 1 }

	qAPResultBand		OBJECT-TYPE
				SYNTAX OCTET STRING
				MAX-ACCESS read-only
				STATUS current
				DESCRIPTION
					"Band of the AP scan result."
				::= { qAPScanEntry 2 }

	qAPResultSSID		OBJECT-TYPE
				SYNTAX OCTET STRING ( SIZE (1..32) )
				MAX-ACCESS read-only
				STATUS current
				DESCRIPTION
					"SSID of the AP scan result."
				::= { qAPScanEntry 3 }

	qAPResultChannel	OBJECT-TYPE
				SYNTAX INTEGER
				MAX-ACCESS read-only
				STATUS current
				DESCRIPTION
					"Channel of the AP scan result."
				::= { qAPScanEntry 4 }


	qAPResultAuthentication	OBJECT-TYPE
				SYNTAX INTEGER { open-system(1), wpa-enterprise(2), wpa2-enterprise(3), wpa-personl(4), wpa2-person(5), none(6), radius-with-8021x(8), unknown(8) }
				MAX-ACCESS read-only
				STATUS current
				DESCRIPTION
					"Authentication of the AP scan result."
				::= { qAPScanEntry 5 }

	qAPResultEncryption	OBJECT-TYPE
				SYNTAX INTEGER { none(1), wep(2), tkip(3), aes(4), tkip-aes(5), unknown(6) }
				MAX-ACCESS read-only
				STATUS current
				DESCRIPTION
					"Encryption of the AP scan result."
				::= { qAPScanEntry 6 }

	qAPResultRssi		OBJECT-TYPE
				SYNTAX INTEGER
				MAX-ACCESS read-only
				STATUS current
				DESCRIPTION
					"Rssi of the AP scan result."
				::= { qAPScanEntry 7 }

	qAPResultBSSID		OBJECT-TYPE
				SYNTAX OCTET STRING
				MAX-ACCESS read-only
				STATUS current
				DESCRIPTION
					"BSSID of the AP scan result."
				::= { qAPScanEntry 8 }

	qAPResultMode		OBJECT-TYPE
				SYNTAX INTEGER { a(1), b(2), an(3), bg(4), bgn(5) }
				MAX-ACCESS read-only
				STATUS current
				DESCRIPTION
					"Mode of the AP scan result."
				::= { qAPScanEntry 9 }

	qAPResultStatus		OBJECT-TYPE
				SYNTAX INTEGER
				MAX-ACCESS read-only
				STATUS current
				DESCRIPTION
					"Status of the AP scan result."
				::= { qAPScanEntry 10 }

--	qWlcBand		OBJECT-TYPE
--				SYNTAX INTEGER { 2g(1), 5g(2) }
--				MAX-ACCESS read-write
--				STATUS current
--				DESCRIPTION ""
--				::= { ap-connection 3 }

	qWlcSsid		OBJECT-TYPE
				SYNTAX OCTET STRING ( SIZE (1..32) )
				MAX-ACCESS read-write
				STATUS current
				DESCRIPTION ""
				::= { ap-connection 4 }

	qWlcAuthentication	OBJECT-TYPE                              
                                SYNTAX INTEGER { open-system(1), shared-key(2), wpa-personal(3), wpa2-personal(4), wpa-enterprise(5), wpa2-enterprise(6), radius-with-8021x(7) }
				MAX-ACCESS read-write
				STATUS current
				DESCRIPTION ""
				::= { ap-connection 5 }

	qWlcWepEncryption	OBJECT-TYPE
				SYNTAX INTEGER { none(1), wep-64bits(2), wep-128bits(3) }
				MAX-ACCESS read-write
				STATUS current
				DESCRIPTION ""
				::= { ap-connection 6 }

	qWlcKeyIndex		OBJECT-TYPE
				SYNTAX INTEGER { first(1), second(2), third(3), forth(4) }
				MAX-ACCESS read-write                      
                                STATUS current
				DESCRIPTION ""
				::= { ap-connection 7 }

	qWlcWepKeyValue		OBJECT-TYPE
                                SYNTAX OCTET STRING
                                MAX-ACCESS read-write
                                STATUS current
                                DESCRIPTION ""
                                ::= { ap-connection  8 }

	qWlcWpaEncryption	OBJECT-TYPE
				SYNTAX INTEGER { tkip(1), aes(2), tkip-aes(3) }
				MAX-ACCESS read-write
				STATUS current
				DESCRIPTION ""
                                ::= { ap-connection 9 }

	qWlcWpaPreSharedKey	OBJECT-TYPE
                                SYNTAX OCTET STRING
                                MAX-ACCESS read-write
                                STATUS current
				DESCRIPTION ""
				::= { ap-connection 10 }

-- ++++++++++++++++++++++++++++++++++++++++++++++++++++++++++++++++++++++
-- *  End of AP Connection Section
-- ++++++++++++++++++++++++++++++++++++++++++++++++++++++++++++++++++++++

-- **********************************************************************
-- *  End of Internet Setup Section 
-- **********************************************************************

-- **********************************************************************
-- *  Router Setup Section 
-- **********************************************************************

-- ++++++++++++++++++++++++++++++++++++++++++++++++++++++++++++++++++++++
-- *  Wireless Setting Section
-- ++++++++++++++++++++++++++++++++++++++++++++++++++++++++++++++++++++++
	
	router-setup		OBJECT IDENTIFIER ::= { quick-internet-setup 2 }

	wireless-setting	OBJECT IDENTIFIER ::= { router-setup 1 }

	networkNameWl2g		OBJECT-TYPE
                                SYNTAX OCTET STRING
                                MAX-ACCESS read-write
				STATUS current
                                DESCRIPTION ""
				::= { wireless-setting 1 }

	networkKeyWl2g		OBJECT-TYPE
                                SYNTAX OCTET STRING
                                MAX-ACCESS read-write
                                STATUS current
				DESCRIPTION ""
				::= { wireless-setting 2 }

--	networkNameWl5g		OBJECT-TYPE
--                                SYNTAX OCTET STRING
--                                MAX-ACCESS read-write
--				STATUS current
--                                DESCRIPTION ""
--				::= { wireless-setting 3 }

--	networkKeyWl5g		OBJECT-TYPE
--                                SYNTAX OCTET STRING
--                                MAX-ACCESS read-write
--                                STATUS current
--				DESCRIPTION ""
--				::= { wireless-setting 4 }

-- ++++++++++++++++++++++++++++++++++++++++++++++++++++++++++++++++++++++
-- *  End of Wireless Section for AP
-- ++++++++++++++++++++++++++++++++++++++++++++++++++++++++++++++++++++++

-- **********************************************************************
-- *  End of Router Setup Section 
-- **********************************************************************

-- ======================================================================
-- * End of Quick Internet Setup Section
-- ======================================================================

END
