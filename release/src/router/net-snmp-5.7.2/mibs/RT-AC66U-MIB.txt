RT-AC66U-MIB DEFINITIONS ::= BEGIN      
	
	IMPORTS MODULE-IDENTITY, OBJECT-TYPE, 
		NOTIFICATION-TYPE,Integer32, Counter32  FROM SNMPv2-SMI 
		DisplayString , MacAddress, RowStatus,
		TruthValue                              FROM SNMPv2-TC
		private, IpAddress, TimeTicks			FROM RFC1155-SMI;

-- **********************************************************************
-- *  Tree Definition  (This should be after MODULE IDENTITY definition in SMIv2.)
-- **********************************************************************		
	enterprises		OBJECT IDENTIFIER ::= { private 1 }
	asus			OBJECT IDENTIFIER ::= { enterprises 2623 }
	asus-wireless	OBJECT IDENTIFIER ::= { asus 4 }
	rtac66u			OBJECT IDENTIFIER ::= { asus-wireless 1 } 
	
-- **********************************************************************
-- *  MODULE IDENTITY
-- **********************************************************************
		rtac66uConfig MODULE-IDENTITY
		LAST-UPDATED "201404010800Z"
		ORGANIZATION "AsusTek"
		CONTACT-INFO " "   
		DESCRIPTION
	        "The MIB module of Asus RT-AC66U."
	    REVISION "201404010800Z"  
		DESCRIPTION
	        "The initial version of Asus RT-AC66U."      
		::= { enterprises 2623 4 1 1 }	 --MODULE-IDENTITY clause must be the first declaration in a module in SMIv2.
										 --But there will be error in MG-SOFT MIB Compiler. 
										     		
-- **********************************************************************
-- *  Major sections
-- **********************************************************************
	wireless				OBJECT IDENTIFIER ::= { rtac66uConfig 1 }	
	lan						OBJECT IDENTIFIER ::= { rtac66uConfig 2 }
	wan						OBJECT IDENTIFIER ::= { rtac66uConfig 3 }
	ipv6					OBJECT IDENTIFIER ::= { rtac66uConfig 4 }
	vpn						OBJECT IDENTIFIER ::= { rtac66uConfig 5 }
	firewall				OBJECT IDENTIFIER ::= { rtac66uConfig 6 }
	administration			OBJECT IDENTIFIER ::= { rtac66uConfig 7 }
	systemLog				OBJECT IDENTIFIER ::= { rtac66uConfig 8 }
	guestNetwork			OBJECT IDENTIFIER ::= { rtac66uConfig 9 }
	trafficManager			OBJECT IDENTIFIER ::= { rtac66uConfig 10 }  
	parentalControl        	OBJECT IDENTIFIER ::= { rtac66uConfig 11 }   
	quickInternetSetup		OBJECT IDENTIFIER ::= { rtac66uConfig 12 }

-- **********************************************************************
-- *  MIB attribute OBJECT-TYPE definitions follow
-- **********************************************************************

-- ======================================================================
-- * Wireless Section
-- ======================================================================
-- **********************************************************************
-- *  2.4G Section
-- **********************************************************************

	wl2g		OBJECT IDENTIFIER ::= { wireless 1 }

-- ++++++++++++++++++++++++++++++++++++++++++++++++++++++++++++++++++++++
-- +  General Section (2.4G)
-- ++++++++++++++++++++++++++++++++++++++++++++++++++++++++++++++++++++++

	generalWl2g	OBJECT IDENTIFIER ::= { wl2g 1 }

	ssidWl2g	OBJECT-TYPE
 				SYNTAX OCTET STRING ( SIZE (1..32) )
				MAX-ACCESS read-write
                STATUS current
                DESCRIPTION
					"The network name or SSID is a unique name that identifies the wireless 
					network. WiFi devices automatically detect all networks within range. 
					Assign an identification string of up to 32 characters for your wireless 
					connection."
                ::= { generalWl2g 1 }

	hideSSIDWl2g	OBJECT-TYPE
                SYNTAX INTEGER { no(0), yes(1) }
				MAX-ACCESS read-write
                STATUS current
				DESCRIPTION
		           	"If [YES] is selected, your SSID does not show in site surveys by wireless 
					mobile clients and they can only connect to your ASUS Wireless Router with 
					your SSID of AP."
				::= { generalWl2g 2 }

	wirelessModeWl2g	OBJECT-TYPE
                SYNTAX INTEGER { auto(0), dot11N-only(1), legacy(2) }
				MAX-ACCESS read-write
				STATUS current
				DESCRIPTION
					"This item allows you to select any of these options for the Wireless Mode 
					of your 802.11n interface. [Auto]: Allows 802.11n, 802.11g, and 802.11b 
					devices to connect to RT-AC66U. [Legacy]: Allows 802.11b/g/n devices to 
					connect to RT-AC66U, but 802.11n devices only run at a speed of 54Mbps. 
					[n Only]: Maximizes performance, but does not allow 802.11g and 802.11b 
					devices to connect to your device."
				::= { generalWl2g 3 }      
				
	optimizedforXboxWl2g	OBJECT-TYPE
                SYNTAX INTEGER { no(0), yes(1) }
				MAX-ACCESS read-write
				STATUS current                                                        
                DESCRIPTION
					""
                ::= { generalWl2g 4 }
			

	protectionWl2g	OBJECT-TYPE
                SYNTAX INTEGER { enable(1), disable(2) }
				MAX-ACCESS read-write
				STATUS current                                                        
                DESCRIPTION
					"Tick b/g Protection to allow b/g devices to connect to RT-AC66U without 
					affecting 11n devices, but this increases the router's workload."
                ::= { generalWl2g 5 }

	channelBandwidthWl2g	OBJECT-TYPE
                SYNTAX INTEGER { b20-or-40MHz(0), b20MHz(1), b40MHz(2) }
				MAX-ACCESS read-write
				STATUS current                                                        
                DESCRIPTION
					"Selecting a wider channel bandwidth provides you with a higher transmission 
					speed. Uses 40MHz coexistent bandwidth to maximize the wireless throughput. 
					If you experience issues with wireless stability, please choose the default 
					mode (20MHz)."
                ::= { generalWl2g 6 }

	controlChannelWl2g	OBJECT-TYPE
                SYNTAX INTEGER
                MAX-ACCESS read-write
                STATUS current
                DESCRIPTION
		        	"The radio channel for wireless connection operation. 0: auto"
                ::= { generalWl2g 7 }

	extensionChannelWl2g	OBJECT-TYPE
                SYNTAX INTEGER { auto(1), below(2), above(3) }
                MAX-ACCESS read-write
                STATUS current
                DESCRIPTION
		        	"Select the extension channel used in the 20/40MHz channel bandwidth mode. 
					802.11n uses the extension channel to get extra speed. For channels 1 to 4, 
					you can only select an upper channel. For channels 5 to 7, you can select a 
					lower or an upper channel as the extension channel. For channels above 7, 
					you can only select a lower channel."
				::= { generalWl2g 8 }

	authenticationWl2g	OBJECT-TYPE                              
                SYNTAX INTEGER { open-system(1), shared-key(2), wpa-personal(3), wpa2-personal(4), wpa-auto-personal(5), wpa-enterprise(6), wpa2-enterprise(7), wpa-auto-enterprise(8), radius-with-8021x(9) }
				MAX-ACCESS read-write
				STATUS current
				DESCRIPTION
					"This field enables the authentication methods for wireless clients."
				::= { generalWl2g 9 }

	wepEncryptionWl2g	OBJECT-TYPE
				SYNTAX INTEGER { none(0), wep-64bits(1), wep-128bits(2) }
				MAX-ACCESS read-write
				STATUS current
				DESCRIPTION 
					"Enable WEP Encyption to encrypt data."
				::= { generalWl2g 10 }

	keyIndexWl2g	OBJECT-TYPE
				SYNTAX INTEGER { first(1), second(2), third(3), forth(4) }
				MAX-ACCESS read-write                      
                STATUS current
				DESCRIPTION
					"Default transmit WEP Key."
				::= { generalWl2g 11 }       
                                
	wl2gWepKeyTable	OBJECT-TYPE
				SYNTAX SEQUENCE OF Wl2gWepKeyEntry
				MAX-ACCESS not-accessible
                STATUS current
                DESCRIPTION
                   	"Wep Key Table."
                ::= { generalWl2g 12 }

	wl2gWepKeyEntry	OBJECT-TYPE
                SYNTAX Wl2gWepKeyEntry
                MAX-ACCESS not-accessible
                STATUS current
                DESCRIPTION ""
                INDEX { wepKeyIndexWl2g }
                ::= { wl2gWepKeyTable 1 }

 	Wl2gWepKeyEntry ::= SEQUENCE {
        		wepKeyIndexWl2g		INTEGER,
        		wepKeyValueWl2g		OCTET STRING
    	}                                    

	wepKeyIndexWl2g	OBJECT-TYPE
                SYNTAX INTEGER ( 1..4 )
                MAX-ACCESS not-accessible
                STATUS current
                DESCRIPTION
                   	"Wep key index."
                ::= { wl2gWepKeyEntry 1 }

	wepKeyValueWl2g	OBJECT-TYPE
                SYNTAX OCTET STRING
                MAX-ACCESS read-write
                STATUS current
                DESCRIPTION
                   	"WEP key value."
                ::= { wl2gWepKeyEntry  2 } 

	passphraseWl2g	OBJECT-TYPE
                SYNTAX OCTET STRING
                MAX-ACCESS read-write
                STATUS current
				DESCRIPTION
					"If you select WEP Encryption, you can key in some words in this field to 
					generate WEP keys automatically."
				::= { generalWl2g 13 } 
                                
	wpaEncryptionWl2g	OBJECT-TYPE
				SYNTAX INTEGER { tkip(1), aes(2), tkip-aes(3), none(0) }
				MAX-ACCESS read-write
				STATUS current
				DESCRIPTION
					"Enable WPA Encryption to encrypt data."   
                                ::= { generalWl2g 14 }

	wpaPreSharedKeyWl2g	OBJECT-TYPE
                SYNTAX OCTET STRING
                MAX-ACCESS read-write
                STATUS current
				DESCRIPTION
					"This field requires a password of 8 and 63 characters(letters, numbers or 
					a combination) or 64 hex digits to start the encryption process ."
				::= { generalWl2g 15 }
				                            
-- /*For Protected Management Frames, only enable for WPA2-Personal and WPA2-Enterprise, ARM platform.*/--				                            
--	protectedManagementFrameWl2g OBJECT-TYPE
--				SYNTAX INTEGER { disable(0), capable(1), required(2) }
--				MAX-ACCESS read-write                      
--              STATUS current
--				DESCRIPTION
--					""
--				::= { generalWl2g 16 }     			
                
	keyRotationIntervalWl2g	OBJECT-TYPE
				SYNTAX INTEGER
				MAX-ACCESS read-write
				STATUS current
				DESCRIPTION
					"This field specifies the interval (in seconds) after which a WPA group key 
					is changed . Enter [0] (zero) to indicate that a periodic key-change is not 
					required."
				::= { generalWl2g 17 }

-- ++++++++++++++++++++++++++++++++++++++++++++++++++++++++++++++++++++++
-- *  End of General Section (2.4G)
-- ++++++++++++++++++++++++++++++++++++++++++++++++++++++++++++++++++++++

-- ++++++++++++++++++++++++++++++++++++++++++++++++++++++++++++++++++++++
-- +  WPS Section (2.4G)
-- ++++++++++++++++++++++++++++++++++++++++++++++++++++++++++++++++++++++

	wpsWl2g		OBJECT IDENTIFIER ::= { wl2g 2 }

	enableWPSWl2g	OBJECT-TYPE
                SYNTAX INTEGER { enable(1), disable(2) }
				MAX-ACCESS read-write
				STATUS current                                                        
                DESCRIPTION
					"Selecting Yes allows Wi-Fi Protected Setup (WPS) to simplify the process of 
					connecting any device to the wireless network. WPS support the authentication 
					of Open system, WPA-Personal, WPA2-Personal. Not support Shared Key, 
					WPA-Enterprise, WPA2-Enterprise and Radius."
				::= { wpsWl2g 1 }  
				
	switchFrequencyTo5g 	OBJECT-TYPE
				SYNTAX INTEGER { yes(1), nothing(2) }
				MAX-ACCESS read-write
               	STATUS current
				DESCRIPTION
	        		"If [YES] is selected, frequency of WPS will be switched to 5G.
	        		This value can be set only when WPS is disabled."
				::= { wpsWl2g 2 }
			

	connectionStatusWl2g	OBJECT-TYPE
                SYNTAX OCTET STRING
                MAX-ACCESS read-only
                STATUS current
                DESCRIPTION ""
                ::= { wpsWl2g 3 }

	configuredWl2g		OBJECT-TYPE
                SYNTAX OCTET STRING
                MAX-ACCESS read-only
                STATUS current
                DESCRIPTION ""
                ::= { wpsWl2g 4 }

	apPinCodeWl2g		OBJECT-TYPE
                SYNTAX OCTET STRING
                MAX-ACCESS read-only
                STATUS current
                DESCRIPTION
					"Key in the router's PIN code in the client's WPS utility and configure the 
					network name and security settings."
                                ::= { wpsWl2g 5 }
                                                                                
	clientPinCodeWl2g	OBJECT-TYPE
                SYNTAX OCTET STRING
				MAX-ACCESS read-write
                STATUS current
                DESCRIPTION ""
                ::= { wpsWl2g 6 }       
                
	wpsMethodWl2g	OBJECT-TYPE
                SYNTAX INTEGER { pbc(1), clientPinCode(2), nothing(3) }
				MAX-ACCESS read-write
				STATUS current                                                        
                DESCRIPTION
					"Selecting PIN (Personal Information Number) you have to enter 
				 	a number to establish a wireless connection. Select PBC (Push Button 
				 	Configuration) you have to push a button to establish a wireless connection."
				::= { wpsWl2g 7 }
                

-- ++++++++++++++++++++++++++++++++++++++++++++++++++++++++++++++++++++++
-- *  End of WPS Section (2.4G)
-- ++++++++++++++++++++++++++++++++++++++++++++++++++++++++++++++++++++++

-- ++++++++++++++++++++++++++++++++++++++++++++++++++++++++++++++++++++++
-- +  Bridge Section (2.4G)
-- ++++++++++++++++++++++++++++++++++++++++++++++++++++++++++++++++++++++

	bridgeWl2g	OBJECT IDENTIFIER ::= { wl2g 3 }
        
    wbMacAddrWl2g	OBJECT-TYPE
				SYNTAX MacAddress
				MAX-ACCESS read-only
				STATUS current
				DESCRIPTION
					"MAC address of 2.4GHz."
				::= { bridgeWl2g  1 } 

	wbApModeWl2g	OBJECT-TYPE
                SYNTAX INTEGER { ap-only(1), wds-only(2), hybrid(3) }
				MAX-ACCESS read-write
				STATUS current
				DESCRIPTION
					"Select [AP Only] to disable Wireless Bridge function. Select [WDS Only] to 
					disable local wireless station connection. Select [Hybrid] to enable Wireless 
					bridge function and wireless stations will be able to connect to the AP."
				::= { bridgeWl2g 2 }

	wbConnectRemoteBridegeAPWl2g	OBJECT-TYPE
				SYNTAX INTEGER { yes(1), no(2) }
				MAX-ACCESS read-write
				STATUS current
				DESCRIPTION
					"Select [Yes] to connect RT-AC66U to other APs listed in the Remote AP List."
				::= { bridgeWl2g 3 }

	wbRemoteBridgeScanWl2g	OBJECT IDENTIFIER ::= { bridgeWl2g 5 }

	wbBridgeAPScanActWl2g	OBJECT-TYPE
				SYNTAX INTEGER { scan(1), nothing(2) }
				MAX-ACCESS read-write
				STATUS current
				DESCRIPTION ""
				::= { wbRemoteBridgeScanWl2g 1 }

	wbWl2gBridgeAPScanTable	OBJECT-TYPE
				SYNTAX SEQUENCE OF WbBridgeAPScanEntryWl2g
				MAX-ACCESS not-accessible
				STATUS current
				DESCRIPTION ""
                ::= { wbRemoteBridgeScanWl2g 2 }          
                                
	wbWl2gBridgeAPScanEntry	OBJECT-TYPE
				SYNTAX WbBridgeAPScanEntryWl2g
				MAX-ACCESS not-accessible
				STATUS current
				DESCRIPTION ""
				INDEX { wbAPResultIndexWl2g }
				::= { wbWl2gBridgeAPScanTable 1 }

 	WbBridgeAPScanEntryWl2g ::= SEQUENCE {
        		wbAPResultIndexWl2g		INTEGER,
        		wbAPResultBSSIDWl2g	    OCTET STRING,
        		wbAPResultSSIDWl2g		OCTET STRING
    	}

	wbAPResultIndexWl2g	OBJECT-TYPE
				SYNTAX INTEGER ( 1..32 )
				MAX-ACCESS not-accessible
				STATUS current
				DESCRIPTION
					"AP scan result entry index."
				::= { wbWl2gBridgeAPScanEntry 1 }

	wbAPResultBSSIDWl2g	OBJECT-TYPE
				SYNTAX OCTET STRING
				MAX-ACCESS read-only
				STATUS current
				DESCRIPTION
					"BSSID of the AP scan result."
				::= { wbWl2gBridgeAPScanEntry  2 }

	wbAPResultSSIDWl2g	OBJECT-TYPE
				SYNTAX OCTET STRING ( SIZE (1..32) )
				MAX-ACCESS read-only
				STATUS current
				DESCRIPTION
					"SSID of the AP scan result."
				::= { wbWl2gBridgeAPScanEntry 3 }

	wbWl2gRemoteAPTable	OBJECT-TYPE
				SYNTAX SEQUENCE OF WBRemoteAPEntryWl2g
				MAX-ACCESS not-accessible
				STATUS current
				DESCRIPTION
					"Remote AP list."
				::= { bridgeWl2g 6 }

	wbRemoteAPEntryWl2g	OBJECT-TYPE
				SYNTAX WBRemoteAPEntryWl2g
				MAX-ACCESS not-accessible
				STATUS current
				DESCRIPTION ""
				INDEX { wbRemoteAPIndexWl2g }
				::= { wbWl2gRemoteAPTable 1 }

 	WBRemoteAPEntryWl2g ::= SEQUENCE {
        		wbRemoteAPIndexWl2g	INTEGER,
        		wbRemoteAPMACAddrWl2g	MacAddress,
        		wbRemoteAPDelEntryWl2g	INTEGER
    	}                           
    
	wbRemoteAPIndexWl2g	OBJECT-TYPE
				SYNTAX INTEGER ( 1..4 )
				MAX-ACCESS not-accessible
				STATUS current
				DESCRIPTION 
					"Remote AP Index."
				::= { wbRemoteAPEntryWl2g 1 }

	wbRemoteAPMACAddrWl2g	OBJECT-TYPE
				SYNTAX MacAddress
				MAX-ACCESS read-write
				STATUS current
				DESCRIPTION
					"MAC address of remote bridge APs."
				::= { wbRemoteAPEntryWl2g  2 } 

	wbRemoteAPDelEntryWl2g	OBJECT-TYPE
				SYNTAX INTEGER { yes(1), no(2) }
				MAX-ACCESS read-write
				STATUS current
				DESCRIPTION
					"Delete the AP enntry."
				::= { wbRemoteAPEntryWl2g 3 }

-- ++++++++++++++++++++++++++++++++++++++++++++++++++++++++++++++++++++++
-- *  End of Bridge Section (2.4G)
-- ++++++++++++++++++++++++++++++++++++++++++++++++++++++++++++++++++++++

-- ++++++++++++++++++++++++++++++++++++++++++++++++++++++++++++++++++++++
-- +  Mac Filter Section (2.4G)
-- ++++++++++++++++++++++++++++++++++++++++++++++++++++++++++++++++++++++

	macFilterWl2g	OBJECT IDENTIFIER ::= { wl2g 4 }

	macFilterModeWl2g	OBJECT-TYPE
				SYNTAX INTEGER { disable(1), accept(2), reject(3) }
				MAX-ACCESS read-write
				STATUS current
				DESCRIPTION
					"In Accept mode, RT-AC66U only accept clients with MAC address in the list. In 
					Reject mode, RT-AC66U will reject clients with MAC address in the list."
				::= { macFilterWl2g 1 }

	wl2gMacFilterTable	OBJECT-TYPE
				SYNTAX SEQUENCE OF MacFilterEntryWl2g
				MAX-ACCESS not-accessible
				STATUS current
				DESCRIPTION
					"Mac filter list."
                ::= { macFilterWl2g 2 }
                                    
	macFilterEntryWl2g	OBJECT-TYPE
				SYNTAX MacFilterEntryWl2g
                MAX-ACCESS not-accessible
				STATUS current
				DESCRIPTION ""
				INDEX { macFilterIndexWl2g }
				::= { wl2gMacFilterTable 1 }

 	MacFilterEntryWl2g ::= SEQUENCE {
        		macFilterIndexWl2g	INTEGER,
        		macFilterMACAddrWl2g	MacAddress,
        		macFilterDelEntryWl2g	INTEGER
    	}                           
    
	macFilterIndexWl2g	OBJECT-TYPE
				SYNTAX INTEGER ( 1..64 )
				MAX-ACCESS not-accessible
				STATUS current
				DESCRIPTION
					"Mac filter list index"
				::= { macFilterEntryWl2g 1 }

	macFilterMACAddrWl2g	OBJECT-TYPE
				SYNTAX MacAddress
				MAX-ACCESS read-write
				STATUS current
				DESCRIPTION
					"MAC address of station which device controls its access."
				::= { macFilterEntryWl2g  2 } 
	
	macFilterDelEntryWl2g	OBJECT-TYPE
				SYNTAX INTEGER { yes(1), no(2) }
				MAX-ACCESS read-write
				STATUS current
				DESCRIPTION
					"Delete the mac filter entry."
				::= { macFilterEntryWl2g 3 }

-- ++++++++++++++++++++++++++++++++++++++++++++++++++++++++++++++++++++++
-- *  End of Mac Filter Section (2.4G)
-- ++++++++++++++++++++++++++++++++++++++++++++++++++++++++++++++++++++++

-- ++++++++++++++++++++++++++++++++++++++++++++++++++++++++++++++++++++++
-- +  Radius Setting Section (2.4G)
-- ++++++++++++++++++++++++++++++++++++++++++++++++++++++++++++++++++++++

	radiusSettingWl2g	OBJECT IDENTIFIER ::= { wl2g 5 }

	radiusServerIPAddrWl2g	OBJECT-TYPE
				SYNTAX OCTET STRING ( SIZE (0..39) )
				MAX-ACCESS read-write
				STATUS current
				DESCRIPTION
					"The IP address of the RADIUS server for wireless authentication and dynamic WEP 
					key derivation."
				::= { radiusSettingWl2g 1 }

	radiusPortWl2g		OBJECT-TYPE
				SYNTAX INTEGER (0..65535)
				MAX-ACCESS read-write
				STATUS current
				DESCRIPTION
					"The UDP port number for connection to the RADIUS server."
                                ::= { radiusSettingWl2g 2 }

	radiusConnectionSecretWl2g	OBJECT-TYPE
				SYNTAX OCTET STRING
				MAX-ACCESS read-write
				STATUS current
				DESCRIPTION
					"The password to connect to the RADIUS server."
				::= { radiusSettingWl2g 3 }

-- ++++++++++++++++++++++++++++++++++++++++++++++++++++++++++++++++++++++
-- *  End of Radius Setting Section (2.4G)
-- ++++++++++++++++++++++++++++++++++++++++++++++++++++++++++++++++++++++

-- ++++++++++++++++++++++++++++++++++++++++++++++++++++++++++++++++++++++
-- +  Professional Section (2.4G)
-- ++++++++++++++++++++++++++++++++++++++++++++++++++++++++++++++++++++++

	professionalWl2g	OBJECT IDENTIFIER ::= { wl2g 6 }

	radioWl2g		OBJECT-TYPE
				SYNTAX INTEGER { yes(1), no(0) }
				MAX-ACCESS read-write
				STATUS current
				DESCRIPTION
					"Select [Yes] to enable radio function."       
				DEFVAL { yes }	                                    
                ::= { professionalWl2g 1 }  
                                
    enableSchedWl2g  OBJECT-TYPE
				SYNTAX INTEGER { yes(1), no(0) }
				MAX-ACCESS read-write
				STATUS current
				DESCRIPTION
					"Select [Yes] to enable wirelss schedule function."                                           
                ::= { professionalWl2g 2 }                                

	weekDaysEnableRadioWl2g	OBJECT-TYPE
				SYNTAX BITS { monday(0), tuesday(1), wednesday(2), thursday(3), friday(4) }
				MAX-ACCESS read-write
				STATUS current
				DESCRIPTION
					"This field defines the dates that wireless function is enabled."
				::= { professionalWl2g 3 }

	weekDaysRadioStartTimeHWl2g	OBJECT-TYPE
				SYNTAX INTEGER ( 0..23 )              
                                MAX-ACCESS read-write
				STATUS current
				DESCRIPTION
					"Hour of starting time of weekdays to enable 2.4G radio."
				::= { professionalWl2g 4 }

	weekDaysRadioStartTimeMWl2g	OBJECT-TYPE
				SYNTAX INTEGER ( 0..59 )
				MAX-ACCESS read-write
				STATUS current
				DESCRIPTION
					"Minute of starting time of weekdays to enable 2.4G radio."
				::= { professionalWl2g 5 }

	weekDaysRadioEndTimeHWl2g	OBJECT-TYPE
				SYNTAX INTEGER ( 0..23 )              
                                MAX-ACCESS read-write
				STATUS current
				DESCRIPTION
					"Hour of ending time of weekdays to enable 2.4G radio."
				::= { professionalWl2g 6 }

	weekDaysRadioEndTimeMWl2g	OBJECT-TYPE
				SYNTAX INTEGER ( 0..59 )
				MAX-ACCESS read-write
				STATUS current
				DESCRIPTION
					"Minute of ending time of weekdays to enable 2.4G radio."
				::= { professionalWl2g 7 }

	weekendEnableRadioWl2g	OBJECT-TYPE
				SYNTAX BITS { saturday(0), sunday(1) }
				MAX-ACCESS read-write
				STATUS current
				DESCRIPTION
					"This field defines the dates that wireless function is enabled."
				::= { professionalWl2g 8 }

	weekendRadioStartTimeHWl2g	OBJECT-TYPE
				SYNTAX INTEGER ( 0..23 )              
                                MAX-ACCESS read-write
				STATUS current
				DESCRIPTION
					"Hour of starting time of weekend to enable 2.4G radio."
				::= { professionalWl2g 9 }

	weekendRadioStartTimeMWl2g	OBJECT-TYPE
				SYNTAX INTEGER ( 0..59 )
				MAX-ACCESS read-write
				STATUS current
				DESCRIPTION
					"Minute of starting time of weekend to enable 2.4G radio."
				::= { professionalWl2g 10 }

	weekendRadioEndTimeHWl2g	OBJECT-TYPE
				SYNTAX INTEGER ( 0..23 )              
                                MAX-ACCESS read-write
				STATUS current
				DESCRIPTION
					"Hour of ending time of weekend to enable 2.4G radio."
				::= { professionalWl2g 11 }

	weekendRadioEndTimeMWl2g	OBJECT-TYPE
				SYNTAX INTEGER ( 0..59 )
				MAX-ACCESS read-write
				STATUS current
				DESCRIPTION
					"Minute of ending time of weekend to enable 2.4G radio."
				::= { professionalWl2g 12 }

	apIsolatedWl2g		OBJECT-TYPE
				SYNTAX INTEGER { yes(1), no(0) }
				MAX-ACCESS read-write
				STATUS current
				DESCRIPTION
					"When this feature is enabled, wireless clients or devices will not be able 
					to communicate with each other. You may want to utilize this feature if you 
					have many guests that frequent your wireless network."
				::= { professionalWl2g 13 } 
				
	roamingAssistantWl2g	OBJECT-TYPE
				SYNTAX INTEGER { disable(0), enable(1) }
				MAX-ACCESS read-write
				STATUS current
				DESCRIPTION
					"In multiple AP or wireless router-repeater environment, client sometimes 
					cannot automatically connect to the AP with better signal because it still 
					connect to main wireless router. Enabling this feature would force disconnecting 
					the client and main router when the signal strength is under the threshold 
					and client can choose the AP with better signal."
				::= { professionalWl2g 14 } 			
                                              
	disconnectClientRSSIWl2g 	OBJECT-TYPE
				SYNTAX INTEGER (-90..-70)
				MAX-ACCESS read-write
				STATUS current
				DESCRIPTION
					"Disconnect clients with RSSI lower than the settings."
				::= { professionalWl2g 15 }
                                              
	igmpSnoopingWl2g	OBJECT-TYPE
				SYNTAX INTEGER { disable(0), enable(1) }
				MAX-ACCESS read-write
				STATUS current
				DESCRIPTION
					"When enabled, IGMP Snooping monitors IGMP communication among devices and 
					optimizes wireless multicast traffic."
				::= { professionalWl2g 16 } 	
				                                              
	multicastRateWl2g	OBJECT-TYPE
				SYNTAX INTEGER { auto(1), rOFDM-6(2), rOFDM-9(3), rOFDM-12(4), rOFDM-18(5), rOFDM-24(6), rOFDM-36(7), rOFDM-48(8), rOFDM-54(9), rCCK-1(10), rCCK-2(11), rCCK-5(12), rCCK-11(13) }
				MAX-ACCESS read-write
				STATUS current
				DESCRIPTION
					"Select the multicast transmission rate. You are recommended to select Auto to 
					maximize performance."
				::= { professionalWl2g 17 }

	preambleTypeWl2g	OBJECT-TYPE
				SYNTAX INTEGER { long(1), short(2), auto(3) }
				MAX-ACCESS read-write
				STATUS current
				DESCRIPTION
					"The Preamble type defines the length of the CRC (Cyclic Redundancy Check) 
					block, which is a technique for detecting data transmission errors among 
					wireless devices. We recommend that you configure all wireless devices to the 
					same preamble type. Use short preamble for wireless devices in high network 
					traffic areas. Use long preamble for older wireless devices."
				::= { professionalWl2g 18 }
              
    aMPDURTSWl2g     OBJECT-TYPE
				SYNTAX INTEGER { disable(0), enable(1) }
				MAX-ACCESS read-write
				STATUS current
				DESCRIPTION
					"Select 'Enable' to use RTS for every AMPDU."
				::= { professionalWl2g 19 }   

	rtsThresholdWl2g	OBJECT-TYPE
				SYNTAX INTEGER (0..2347)
				MAX-ACCESS read-write
				STATUS current
				DESCRIPTION
					"Lower the signal RTS (Request To Send) to promote the transmission efficiency 
					in condition of noisy environment or too many clients."
				::= { professionalWl2g 20 }

	dtimIntervalWl2g	OBJECT-TYPE
				SYNTAX INTEGER (1..255)
				MAX-ACCESS read-write
				STATUS current
				DESCRIPTION
					"DTIM (Delivery Traffic Indication Message) is included in Beacon packet.The 
					DTIM Interval (1-255) means the period of time to wake up wireless clients from 
					Sleep Mode. The default value is 3."
				::= { professionalWl2g 21 }

	beaconIntervalWl2g	OBJECT-TYPE
				SYNTAX INTEGER (20..1000)
				MAX-ACCESS read-write
				STATUS current
				DESCRIPTION
					"Beacon Interval means the period of time between one beacon and the next one. 
					The default value is 100 (the unit is millisecond, or 1/1000 second). Lower the 
					Beacon Interval to improve transmission performance in unstable environment or for 
					roaming clients, but it will be power consuming."
				::= { professionalWl2g 22 }

	txBurstingWl2g		OBJECT-TYPE
				SYNTAX INTEGER { enable(1), disable(2) }
				MAX-ACCESS read-write
				STATUS current
				DESCRIPTION
					"Selecting [Enable] enables TX Bursting to improve the transmission speed (from AP 
					to client) of g devices."
				::= { professionalWl2g 23 }
				
	wmmAPSDWl2g		OBJECT-TYPE
				SYNTAX INTEGER { enable(1), disable(2) }
				MAX-ACCESS read-write
				STATUS current
				DESCRIPTION
					"Enable or Disable WMM APSD (Automatic Power Save Delivery)."
				::= { professionalWl2g 24 }             
				                                                               
	optimizeAMPDUAggregWl2g OBJECT-TYPE
				SYNTAX INTEGER { disable(0), enable(1) }
				MAX-ACCESS read-write
				STATUS current
				DESCRIPTION
					"Optimize max number of mpdus in an AMDPU."
				::= { professionalWl2g 25 }
                                   
	optimizeAckSuppressionWl2g OBJECT-TYPE
				SYNTAX INTEGER { disable(0), enable(1) }
				MAX-ACCESS read-write
				STATUS current
				DESCRIPTION
					"Optimize max number of ack to suppress in a row."
				::= { professionalWl2g 26 }
	
	txPowerAdjustmentWl2g	OBJECT-TYPE
				SYNTAX INTEGER (0..100)
				MAX-ACCESS read-write
				STATUS current
				DESCRIPTION
					"Increase Tx Power to enhance the transmission quality or decrease Tx Power to reduce 
					power consumption."
				::= { professionalWl2g 27 }

-- ++++++++++++++++++++++++++++++++++++++++++++++++++++++++++++++++++++++
-- *  End of Professional Section (2.4G)
-- ++++++++++++++++++++++++++++++++++++++++++++++++++++++++++++++++++++++

-- **********************************************************************
-- *  End of 2.4G Section
-- **********************************************************************


-- **********************************************************************
-- *  5G Section
-- **********************************************************************

	wl5g		OBJECT IDENTIFIER ::= { wireless 2 }

-- ++++++++++++++++++++++++++++++++++++++++++++++++++++++++++++++++++++++
-- +  General Section (5G)
-- ++++++++++++++++++++++++++++++++++++++++++++++++++++++++++++++++++++++

	generalWl5g		OBJECT IDENTIFIER ::= { wl5g 1 }

	ssidWl5g	OBJECT-TYPE
 				SYNTAX OCTET STRING ( SIZE (1..32) )
 				MAX-ACCESS read-write
 				STATUS current
 				DESCRIPTION
					"The network name or SSID is a unique name that identifies the wireless 
					network. WiFi devices automatically detect all networks within range. 
					Assign an identification string of up to 32 characters for your wireless 
					connection."
 				::= { generalWl5g 1 }

	hideSSIDWl5g	OBJECT-TYPE
				SYNTAX INTEGER { no(0), yes(1) }
				MAX-ACCESS read-write
                STATUS current
				DESCRIPTION
		        	"If [YES] is selected, your SSID does not show in site surveys by wireless 
					mobile clients and they can only connect to your ASUS Wireless Router with 
					your SSID of AP."
				::= { generalWl5g 2 }

	wirelessModeWl5g	OBJECT-TYPE
 				SYNTAX INTEGER { auto(0), n-ac(1), legacy(2) }
				MAX-ACCESS read-write
				STATUS current
				DESCRIPTION
					"This item allows you to select any of these options for the Wireless Mode 
					of your 802.11n interface. [Auto]: Allows 802.11n, 802.11g, and 802.11b 
					devices to connect to RT-AC66U. [Legacy]: Allows 802.11b/g/n devices to 
					connect to RT-AC66U, but 802.11n devices only run at a speed of 54Mbps. 
					[n Only]: Maximizes performance, but does not allow 802.11g and 802.11b 
					devices to connect to your device."
				::= { generalWl5g 3 }

	optimizedforXboxWl5g	OBJECT-TYPE
                SYNTAX INTEGER { no(0), yes(1) }
				MAX-ACCESS read-write
				STATUS current                                                        
                DESCRIPTION ""
                ::= { generalWl5g 4 }

	channelBandwidthWl5g	OBJECT-TYPE
                SYNTAX INTEGER { b20-40-80MHz(0), b20MHz(1), b40MHz(2), b80MHz(3) }
				MAX-ACCESS read-write
				STATUS current                                                        
                DESCRIPTION
					"Selecting a wider channel bandwidth provides you with a higher transmission 
					speed. Uses 40MHz coexistent bandwidth to maximize the wireless throughput. 
					If you experience issues with wireless stability, please choose the default 
					mode (20MHz)."
               ::= { generalWl5g 5 }

	controlChannelWl5g	OBJECT-TYPE
                SYNTAX INTEGER
                MAX-ACCESS read-write
                STATUS current
                DESCRIPTION
		        	"The radio channel for wireless connection operation. 0: auto"
 				::= { generalWl5g 6 }

	extensionChannelWl5g	OBJECT-TYPE
                SYNTAX INTEGER { auto(1) }
                MAX-ACCESS read-only
                STATUS current
                DESCRIPTION ""
				::= { generalWl5g 7 }
				
	authenticationWl5g	OBJECT-TYPE                              
                SYNTAX INTEGER { opensystem(1), sharedkey(2), wpa-personal(3), wpa2-personal(4), wpa-auto-personal(5), wpa-enterprise(6), wpa2-enterprise(7), wpa-auto-enterprise(8), radius-with-8021x(9) }
				MAX-ACCESS read-write
				STATUS current
				DESCRIPTION
					"This field enables the authentication methods for wireless clients."
				::= { generalWl5g 8 }

	wepEncryptionWl5g	OBJECT-TYPE
				SYNTAX INTEGER { none(0), wep-64bits(1), wep-128bits(2) }
				MAX-ACCESS read-write
				STATUS current
				DESCRIPTION 
					"Enable WEP Encyption to encrypt data."
				::= { generalWl5g 9 }

	keyIndexWl5g	OBJECT-TYPE
				SYNTAX INTEGER { first(1), second(2), third(3), forth(4) }
				MAX-ACCESS read-write                      
                STATUS current
				DESCRIPTION
					"Default transmit WEP Key."
				::= { generalWl5g 10 }       
                                
	wl5gWepKeyTable		OBJECT-TYPE
				SYNTAX SEQUENCE OF WepKeyEntryWl5g
				MAX-ACCESS not-accessible
                STATUS current
                DESCRIPTION
                   	"Wep Key Table."
                ::= { generalWl5g 11 }

	wepKeyEntryWl5g		OBJECT-TYPE
                SYNTAX WepKeyEntryWl5g
                MAX-ACCESS not-accessible
                STATUS current
                DESCRIPTION ""
                INDEX { wepKeyIndexWl5g }
                ::= { wl5gWepKeyTable 1 }

 	WepKeyEntryWl5g ::= SEQUENCE {
        		wepKeyIndexWl5g		INTEGER,
        		wepKeyValueWl5g		OCTET STRING
    	}                                    

	wepKeyIndexWl5g		OBJECT-TYPE
                SYNTAX INTEGER ( 1..4 )
                MAX-ACCESS not-accessible
                STATUS current
                DESCRIPTION
                	"Wep key index"
                ::= { wepKeyEntryWl5g 1 }

	wepKeyValueWl5g		OBJECT-TYPE
                SYNTAX OCTET STRING
                MAX-ACCESS read-write
                STATUS current
                DESCRIPTION
                   	"WEP key value"
                ::= { wepKeyEntryWl5g  2 } 

	passphraseWl5g		OBJECT-TYPE
                SYNTAX OCTET STRING
                MAX-ACCESS read-write
                STATUS current
				DESCRIPTION
					"If you select WEP Encryption, you can key in some words in this field to 
					generate WEP keys automatically."
				::= { generalWl5g 12 } 
                                
	wpaEncryptionWl5g	OBJECT-TYPE
				SYNTAX INTEGER { tkip(1), aes(2), tkip-aes(3), none(0) }
				MAX-ACCESS read-write
				STATUS current
				DESCRIPTION
					"Enable WPA Encryption to encrypt data."   
                ::= { generalWl5g 13 }

	wpaPreSharedKeyWl5g	OBJECT-TYPE
                SYNTAX OCTET STRING
                MAX-ACCESS read-write
                STATUS current
				DESCRIPTION
					"This field requires a password of 8 and 63 characters(letters, numbers or 
					a combination) or 64 hex digits to start the encryption process ."
				::= { generalWl5g 14 }
                               
-- /*For Protected Management Frames, only enable for WPA2-Personal and WPA2-Enterprise, ARM platform.*/--	                               
--    protectedManagementFrameWl5g  OBJECT-TYPE
--				SYNTAX INTEGER { disable(0), capable(1), required(2) }
--				MAX-ACCESS read-write
--				STATUS current
--				DESCRIPTION	""   
--                ::= { generalWl5g 15 }

	keyRotationIntervalWl5g	OBJECT-TYPE
				SYNTAX INTEGER
				MAX-ACCESS read-write
				STATUS current
				DESCRIPTION
					"This field specifies the interval (in seconds) after which a WPA group key 
					is changed . Enter [0] (zero) to indicate that a periodic key-change is not 
					required."
				::= { generalWl5g 16 }

-- ++++++++++++++++++++++++++++++++++++++++++++++++++++++++++++++++++++++
-- *  End of General Section (5G)
-- ++++++++++++++++++++++++++++++++++++++++++++++++++++++++++++++++++++++

-- ++++++++++++++++++++++++++++++++++++++++++++++++++++++++++++++++++++++
-- +  WPS Section (5G)
-- ++++++++++++++++++++++++++++++++++++++++++++++++++++++++++++++++++++++

	wpsWl5g			OBJECT IDENTIFIER ::= { wl5g 2 }

	enableWPSWl5g	OBJECT-TYPE
                    SYNTAX INTEGER { enable(1), disable(2) }
					MAX-ACCESS read-write
					STATUS current                                                        
                    DESCRIPTION
					"Selecting Yes allows Wi-Fi Protected Setup (WPS) to simplify the process of 
					connecting any device to the wireless network. WPS support the authentication 
					of Open system, WPA-Personal, WPA2-Personal. Not support Shared Key, 
					WPA-Enterprise, WPA2-Enterprise and Radius."
				::= { wpsWl5g 1 }      

	switchFrequencyTo2g 	OBJECT-TYPE
					SYNTAX INTEGER { yes(1), nothing(2) }
					MAX-ACCESS read-write
                	STATUS current
					DESCRIPTION
		        		"If [YES] is selected, frequency of WPS will be switched to 2.4G. 
		        		This value can be set only when WPS is disabled."
				::= { wpsWl5g 2 }
 				

	connectionStatusWl5g	OBJECT-TYPE
                    SYNTAX OCTET STRING
                    MAX-ACCESS read-only
                    STATUS current
                    DESCRIPTION ""
                    ::= { wpsWl5g  3 }

	configuredWl5g	OBJECT-TYPE
                    SYNTAX OCTET STRING
                    MAX-ACCESS read-only
                    STATUS current
                    DESCRIPTION ""
                    ::= { wpsWl5g  4 }

	apPinCodeWl5g	OBJECT-TYPE
                    SYNTAX OCTET STRING
                    MAX-ACCESS read-only
                    STATUS current
                    DESCRIPTION
					"Key in the router's PIN code in the client's WPS utility and configure the 
					network name and security settings."
                    ::= { wpsWl5g  5 }
                                      	                                      
	clientPinCodeWl5g	OBJECT-TYPE
                   SYNTAX OCTET STRING
				   MAX-ACCESS read-write
                   STATUS current
                   DESCRIPTION ""
                   ::= { wpsWl5g 6 }  
                   
	wpsMethodWl5g	OBJECT-TYPE
                	SYNTAX INTEGER { pbc(1), clientPinCode(2), nothing(3) }
					MAX-ACCESS read-write
					STATUS current                                                        
                	DESCRIPTION
						"Selecting PIN (Personal Information Number) you have to enter 
					 	a number to establish a wireless connection. Select PBC (Push Button 
					 	Configuration) you have to push a button to establish a wireless connection."
					::= { wpsWl5g 7 }
                   

-- ++++++++++++++++++++++++++++++++++++++++++++++++++++++++++++++++++++++
-- *  End of WPS Section (5G)
-- ++++++++++++++++++++++++++++++++++++++++++++++++++++++++++++++++++++++

-- ++++++++++++++++++++++++++++++++++++++++++++++++++++++++++++++++++++++
-- +  Bridge Section (5G)
-- ++++++++++++++++++++++++++++++++++++++++++++++++++++++++++++++++++++++

	bridgeWl5g	OBJECT IDENTIFIER ::= { wl5g 3 }             
	
    wbMacAddrWl5g	OBJECT-TYPE
				SYNTAX MacAddress
				MAX-ACCESS read-only
				STATUS current
				DESCRIPTION
					"MAC address of 5GHz."
				::= { bridgeWl5g  1 } 


	wbApModeWl5g	OBJECT-TYPE
                SYNTAX INTEGER { ap-only(1), wds-only(2), hybrid(3) }
				MAX-ACCESS read-write
				STATUS current
				DESCRIPTION
					"Select [AP Only] to disable Wireless Bridge function. Select [WDS Only] to 
					disable local wireless station connection. Select [Hybrid] to enable Wireless 
					bridge function and wireless stations will be able to connect to the AP."
				::= { bridgeWl5g 2 }

	wbConnectRemoteBridegeAPWl5g	OBJECT-TYPE
				SYNTAX INTEGER { yes(1), no(2) }
				MAX-ACCESS read-write
				STATUS current
				DESCRIPTION
					"Select [Yes] to connect RT-AC66U to other APs listed in the Remote AP List."
				::= { bridgeWl5g 3 }

	wbRemoteBridgeScanWl5g	OBJECT IDENTIFIER ::= { bridgeWl5g 5 }

	wbBridgeAPScanActWl5g	OBJECT-TYPE
				SYNTAX INTEGER { scan(1), nothing(2) }
				MAX-ACCESS read-write
				STATUS current
				DESCRIPTION ""
				::= { wbRemoteBridgeScanWl5g 1 }

	wbWl5gBridgeAPScanTable	OBJECT-TYPE
				SYNTAX SEQUENCE OF WbBridgeAPScanEntryWl5g
				MAX-ACCESS not-accessible
				STATUS current
				DESCRIPTION ""
                ::= { wbRemoteBridgeScanWl5g 2 }

	wbBridgeAPScanEntryWl5g	OBJECT-TYPE
				SYNTAX WbBridgeAPScanEntryWl5g
				MAX-ACCESS not-accessible
				STATUS current
				DESCRIPTION ""
				INDEX { wbAPResultIndexWl5g }
				::= { wbWl5gBridgeAPScanTable 1 }

 	WbBridgeAPScanEntryWl5g ::= SEQUENCE {
        		wbAPResultIndexWl5g    		INTEGER,
        		wbAPResultBSSIDWl5g	        OCTET STRING,
        		wbAPResultSSIDWl5g			OCTET STRING
    	}

	wbAPResultIndexWl5g	OBJECT-TYPE
				SYNTAX INTEGER ( 1..32 )
				MAX-ACCESS not-accessible
				STATUS current
				DESCRIPTION
					"AP scan result entry index."
				::= { wbBridgeAPScanEntryWl5g 1 }

	wbAPResultBSSIDWl5g	OBJECT-TYPE
				SYNTAX OCTET STRING
				MAX-ACCESS read-only
				STATUS current
				DESCRIPTION
					"BSSID of the AP scan result."
				::= { wbBridgeAPScanEntryWl5g  2 }

	wbAPResultSSIDWl5g	OBJECT-TYPE
				SYNTAX OCTET STRING ( SIZE (1..32) )
				MAX-ACCESS read-only
				STATUS current
				DESCRIPTION
					"SSID of the AP scan result."
				::= { wbBridgeAPScanEntryWl5g 3 }

	wbWl5gRemoteAPTable	OBJECT-TYPE
				SYNTAX SEQUENCE OF WBRemoteAPEntryWl5g
				MAX-ACCESS not-accessible
				STATUS current
				DESCRIPTION
					"Remote AP list."
				::= { bridgeWl5g 6 }

	wbRemoteAPEntryWl5g	OBJECT-TYPE
				SYNTAX WBRemoteAPEntryWl5g
				MAX-ACCESS not-accessible
				STATUS current
				DESCRIPTION ""
				INDEX { wbRemoteAPIndexWl5g }
				::= { wbWl5gRemoteAPTable 1 }

 	WBRemoteAPEntryWl5g ::= SEQUENCE {
        		wbRemoteAPIndexWl5g	INTEGER,
        		wbRemoteAPMACAddrWl5g	MacAddress,
        		wbRemoteAPDelEntryWl5g	INTEGER
    	}                           
    
	wbRemoteAPIndexWl5g	OBJECT-TYPE
				SYNTAX INTEGER ( 1..4 )
				MAX-ACCESS not-accessible
				STATUS current
				DESCRIPTION 
					"Remote AP Index."
				::= { wbRemoteAPEntryWl5g 1 }

	wbRemoteAPMACAddrWl5g	OBJECT-TYPE
				SYNTAX MacAddress
				MAX-ACCESS read-write
				STATUS current
				DESCRIPTION
					"MAC address of remote bridge APs."
				::= { wbRemoteAPEntryWl5g  2 } 

	wbRemoteAPDelEntryWl5g	OBJECT-TYPE
				SYNTAX INTEGER { yes(1), no(2) }
				MAX-ACCESS read-write
				STATUS current
				DESCRIPTION
					"Delete the AP enntry."
				::= { wbRemoteAPEntryWl5g 3 }

-- ++++++++++++++++++++++++++++++++++++++++++++++++++++++++++++++++++++++
-- *  End of Bridge Section (5G)
-- ++++++++++++++++++++++++++++++++++++++++++++++++++++++++++++++++++++++

-- ++++++++++++++++++++++++++++++++++++++++++++++++++++++++++++++++++++++
-- +  Mac Filter Section (5G)
-- ++++++++++++++++++++++++++++++++++++++++++++++++++++++++++++++++++++++

	macFilterWl5g		OBJECT IDENTIFIER ::= { wl5g 4 }

	macFilterModeWl5g	OBJECT-TYPE
				SYNTAX INTEGER { disable(1), accept(2), reject(3) }
				MAX-ACCESS read-write
				STATUS current
				DESCRIPTION
					"In Accept mode, RT-AC66U only accept clients with MAC address in the list. In 
					Reject mode, RT-AC66U will reject clients with MAC address in the list."
				::= { macFilterWl5g 1 }

	wl5gMacFilterTable	OBJECT-TYPE
				SYNTAX SEQUENCE OF MacFilterEntryWl5g
				MAX-ACCESS not-accessible
				STATUS current
				DESCRIPTION
					"Mac filter list."
                ::= { macFilterWl5g 2 }
                                    
	macFilterEntryWl5g	OBJECT-TYPE
				SYNTAX MacFilterEntryWl5g
                MAX-ACCESS not-accessible
				STATUS current
				DESCRIPTION ""
				INDEX { macFilterIndexWl5g }
				::= { wl5gMacFilterTable 1 }

 	MacFilterEntryWl5g ::= SEQUENCE {
        		macFilterIndexWl5g		INTEGER,
        		macFilterMACAddrWl5g	MacAddress,
        		macFilterDelEntryWl5g	INTEGER
    	}                           
    
	macFilterIndexWl5g	OBJECT-TYPE
				SYNTAX INTEGER ( 1..64 )
				MAX-ACCESS not-accessible
				STATUS current
				DESCRIPTION
					"Mac filter list index"
				::= { macFilterEntryWl5g 1 }

	macFilterMACAddrWl5g	OBJECT-TYPE
				SYNTAX MacAddress
				MAX-ACCESS read-write
				STATUS current
				DESCRIPTION
					"MAC address of station which device controls its access."
				::= { macFilterEntryWl5g  2 } 
	
	macFilterDelEntryWl5g	OBJECT-TYPE
				SYNTAX INTEGER { yes(1), no(2) }
				MAX-ACCESS read-write
				STATUS current
				DESCRIPTION
					"Delete the mac filter entry."
				::= { macFilterEntryWl5g 3 }

-- ++++++++++++++++++++++++++++++++++++++++++++++++++++++++++++++++++++++
-- *  End of Mac Filter Section (5G)
-- ++++++++++++++++++++++++++++++++++++++++++++++++++++++++++++++++++++++

-- ++++++++++++++++++++++++++++++++++++++++++++++++++++++++++++++++++++++
-- +  Radius Setting Section (5G)
-- ++++++++++++++++++++++++++++++++++++++++++++++++++++++++++++++++++++++

	radiusSettingWl5g	OBJECT IDENTIFIER ::= { wl5g 5 }

	radiusServerIPAddrWl5g	OBJECT-TYPE
				SYNTAX OCTET STRING ( SIZE (0..39) )
				MAX-ACCESS read-write
				STATUS current
				DESCRIPTION
					"The IP address of the RADIUS server for wireless authentication and dynamic WEP 
					key derivation."
				::= { radiusSettingWl5g 1 }

	radiusPortWl5g		OBJECT-TYPE
				SYNTAX INTEGER (0..65535)
				MAX-ACCESS read-write
				STATUS current
				DESCRIPTION
					"The UDP port number for connection to the RADIUS server."
                ::= { radiusSettingWl5g 2 }

	radiusConnectionSecretWl5g	OBJECT-TYPE
				SYNTAX OCTET STRING
				MAX-ACCESS read-write
				STATUS current
				DESCRIPTION
					"The password to connect to the RADIUS server."
				::= { radiusSettingWl5g 3 }

-- ++++++++++++++++++++++++++++++++++++++++++++++++++++++++++++++++++++++
-- *  End of Radius Setting Section (5G)
-- ++++++++++++++++++++++++++++++++++++++++++++++++++++++++++++++++++++++

-- ++++++++++++++++++++++++++++++++++++++++++++++++++++++++++++++++++++++
-- +  Professional Section (5G)
-- ++++++++++++++++++++++++++++++++++++++++++++++++++++++++++++++++++++++

	professionalWl5g	OBJECT IDENTIFIER ::= { wl5g 6 }

	radioWl5g	OBJECT-TYPE
				SYNTAX INTEGER { yes(1), no(0) }
				MAX-ACCESS read-write
				STATUS current
				DESCRIPTION
					"Select [Yes] to enable radio function."   
				DEFVAL { yes }                                         
                ::= { professionalWl5g 1 }
                  
    enableSchedWl5g  OBJECT-TYPE
				SYNTAX INTEGER { yes(1), no(0) }
				MAX-ACCESS read-write
				STATUS current
				DESCRIPTION
					"Select [Yes] to enable wirelss schedule function."                                           
                ::= { professionalWl5g 2 }
            
	weekDaysEnableRadioWl5g	OBJECT-TYPE
				SYNTAX BITS { monday(0), tuesday(1), wednesday(2), thursday(3), friday(4) }
				MAX-ACCESS read-write
				STATUS current
				DESCRIPTION
					"This field defines the dates that wireless function is enabled."
				::= { professionalWl5g 3 }

	weekDaysRadioStartTimeHWl5g	OBJECT-TYPE
				SYNTAX INTEGER ( 0..23 )              
                MAX-ACCESS read-write
				STATUS current
				DESCRIPTION
					"Hour of starting time of weekdays to enable 5G radio."
				::= { professionalWl5g 4 }

	weekDaysRadioStartTimeMWl5g	OBJECT-TYPE
				SYNTAX INTEGER ( 0..59 )
				MAX-ACCESS read-write
				STATUS current
				DESCRIPTION
					"Minute of starting time of weekdays to enable 5G radio."
				::= { professionalWl5g 5 }

	weekDaysRadioEndTimeHWl5g	OBJECT-TYPE
				SYNTAX INTEGER ( 0..23 )              
                MAX-ACCESS read-write
				STATUS current
				DESCRIPTION
					"Hour of ending time of weekdays to enable 5G radio."
				::= { professionalWl5g 6 }

	weekDaysRadioEndTimeMWl5g	OBJECT-TYPE
				SYNTAX INTEGER ( 0..59 )
				MAX-ACCESS read-write
				STATUS current
				DESCRIPTION
					"Minute of ending time of weekdays to enable 5G radio."
				::= { professionalWl5g 7 }

	weekendEnableRadioWl5g	OBJECT-TYPE
				SYNTAX BITS { saturday(0), sunday(1) }
				MAX-ACCESS read-write
				STATUS current
				DESCRIPTION
					"This field defines the dates that wireless function is enabled."
				::= { professionalWl5g 8 }

	weekendRadioStartTimeHWl5g	OBJECT-TYPE
				SYNTAX INTEGER ( 0..23 )              
                MAX-ACCESS read-write
				STATUS current
				DESCRIPTION
					"Hour of starting time of weekend to enable 2.4G radio."
				::= { professionalWl5g 9 }

	weekendRadioStartTimeMWl5g	OBJECT-TYPE
				SYNTAX INTEGER ( 0..59 )
				MAX-ACCESS read-write
				STATUS current
				DESCRIPTION
					"Minute of starting time of weekend to enable 2.4G radio."
				::= { professionalWl5g 10 }

	weekendRadioEndTimeHWl5g	OBJECT-TYPE
				SYNTAX INTEGER ( 0..23 )              
                MAX-ACCESS read-write
				STATUS current
				DESCRIPTION
					"Hour of ending time of weekend to enable 2.4G radio."
				::= { professionalWl5g 11 }

	weekendRadioEndTimeMWl5g	OBJECT-TYPE
				SYNTAX INTEGER ( 0..59 )
				MAX-ACCESS read-write
				STATUS current
				DESCRIPTION
					"Minute of ending time of weekend to enable 2.4G radio."
				::= { professionalWl5g 12 }

	apIsolatedWl5g		OBJECT-TYPE
				SYNTAX INTEGER { yes(1), no(0) }
				MAX-ACCESS read-write
				STATUS current
				DESCRIPTION
					"When this feature is enabled, wireless clients or devices will not be able 
					to communicate with each other. You may want to utilize this feature if you 
					have many guests that frequent your wireless network."
				::= { professionalWl5g 13 }

	roamingAssistantWl5g	OBJECT-TYPE
				SYNTAX INTEGER { disable(0), enable(1) }
				MAX-ACCESS read-write
				STATUS current
				DESCRIPTION
					"In multiple AP or wireless router-repeater environment, client sometimes 
					cannot automatically connect to the AP with better signal because it still 
					connect to main wireless router. Enabling this feature would force disconnecting 
					the client and main router when the signal strength is under the threshold 
					and client can choose the AP with better signal."
				::= { professionalWl5g 14 }  
				
	disconnectClientRSSIWl5g 	OBJECT-TYPE
				SYNTAX INTEGER
				MAX-ACCESS read-write
				STATUS current
				DESCRIPTION
					"Disconnect clients with RSSI lower than the settings."
				::= { professionalWl5g 15 }
				  				
	igmpSnoopingWl5g	OBJECT-TYPE
				SYNTAX INTEGER { disable(0), enable(1) }
				MAX-ACCESS read-write
				STATUS current
				DESCRIPTION
					"When enabled, IGMP Snooping monitors IGMP communication among devices and 
					optimizes wireless multicast traffic."
				::= { professionalWl5g 16 } 				
				
	multicastRateWl5g	OBJECT-TYPE
				SYNTAX INTEGER { auto(1), rOFDM-6(2), rOFDM-9(3), rOFDM-12(4), rOFDM-18(5), rOFDM-24(6), rOFDM-36(7), rOFDM-48(8), rOFDM-54(9) }
				MAX-ACCESS read-write
				STATUS current
				DESCRIPTION
					"Select the multicast transmission rate. You are recommended to select Auto to 
					maximize performance."
				::= { professionalWl5g 17 }

	preambleTypeWl5g	OBJECT-TYPE
				SYNTAX INTEGER { long(1), short(2), auto(3) }
				MAX-ACCESS read-write
				STATUS current
				DESCRIPTION
					"The Preamble type defines the length of the CRC (Cyclic Redundancy Check) 
					block, which is a technique for detecting data transmission errors among 
					wireless devices. We recommend that you configure all wireless devices to the 
					same preamble type. Use short preamble for wireless devices in high network 
					traffic areas. Use long preamble for older wireless devices."
				::= { professionalWl5g 18 }
                    
    fragThresholdWl5g     OBJECT-TYPE
				SYNTAX INTEGER (256..2346)
				MAX-ACCESS read-write
				STATUS current
				DESCRIPTION
					"Fragmentation Threshold sets the frame size of incoming messages (ranging from 
					256 to 2346 bytes) used as fragmentation boundary. If the frame size is too big, 
					the heavy interference affects transmission reliability. If the frame size is 
					too small, it decreases transmission efficiency."
				::= { professionalWl5g 19 }   
                    
	rtsThresholdWl5g	OBJECT-TYPE
				SYNTAX INTEGER (0..2347)
				MAX-ACCESS read-write
				STATUS current
				DESCRIPTION
					"Lower the signal RTS (Request To Send) to promote the transmission efficiency 
					in condition of noisy environment or too many clients."
				::= { professionalWl5g 20 }

	dtimIntervalWl5g	OBJECT-TYPE
				SYNTAX INTEGER (1..255)
				MAX-ACCESS read-write
				STATUS current
				DESCRIPTION
					"DTIM (Delivery Traffic Indication Message) is included in Beacon packet.The 
					DTIM Interval (1-255) means the period of time to wake up wireless clients from 
					Sleep Mode. The default value is 3."
				::= { professionalWl5g 21 }

	beaconIntervalWl5g	OBJECT-TYPE
				SYNTAX INTEGER (20..1000)
				MAX-ACCESS read-write
				STATUS current
				DESCRIPTION
					"Beacon Interval means the period of time between one beacon and the next one. 
					The default value is 100 (the unit is millisecond, or 1/1000 second). Lower the 
					Beacon Interval to improve transmission performance in unstable environment or for 
					roaming clients, but it will be power consuming."
				::= { professionalWl5g 22 }

	txBurstingWl5g		OBJECT-TYPE
				SYNTAX INTEGER { enable(1), disable(2) }
				MAX-ACCESS read-write
				STATUS current
				DESCRIPTION
					"Selecting [Enable] enables TX Bursting to improve the transmission speed (from AP 
					to client) of g devices."
				::= { professionalWl5g 23 }     

	wmmWl5g			OBJECT-TYPE
				SYNTAX INTEGER { auto(1), enable(2), disable(3) }
				MAX-ACCESS read-write
				STATUS current
				DESCRIPTION
					"Enable WMM (Wi-Fi Multimedia) to improve user experience of multimedia applications 
					on your wireless network."
				::= { professionalWl5g 24 }

	wmmNoAcknowledgementWl5g			OBJECT-TYPE
				SYNTAX INTEGER { enable(1), disable(2) }
				MAX-ACCESS read-write
				STATUS current
				DESCRIPTION
					"[No-Acknowledgement] is the acknowledge policy at MAC level. When enabled, it results 
					in more efficient throughput but higher error rates in a noisy Radio Frequency (RF) 
					environment."
				::= { professionalWl5g 25 }				

	wmmAPSDWl5g		OBJECT-TYPE
				SYNTAX INTEGER { enable(1), disable(2) }
				MAX-ACCESS read-write
				STATUS current
				DESCRIPTION
					"Enable or Disable WMM APSD (Automatic Power Save Delivery)."
				::= { professionalWl5g 26 }   
				
	optimizeAMPDUAggregWl5g OBJECT-TYPE
				SYNTAX INTEGER { disable(0), enable(1) }
				MAX-ACCESS read-write
				STATUS current
				DESCRIPTION
					"Optimize max number of mpdus in an AMDPU."
				::= { professionalWl5g 27 }
                                   
	optimizeAckSuppressionWl5g OBJECT-TYPE
				SYNTAX INTEGER { disable(0), enable(1) }
				MAX-ACCESS read-write
				STATUS current
				DESCRIPTION
					"Optimize max number of ack to suppress in a row."
				::= { professionalWl5g 28 }
	
	explicitBeamformingWl5g OBJECT-TYPE
				SYNTAX INTEGER { disable(0), enable(1) }
				MAX-ACCESS read-write
				STATUS current
				DESCRIPTION
					"The client's WLAN adapter and router both support beamforming technology. 
					This technology allows these devices to communicate the channel estimation 
					and steering direction to each other to improve download and uplink speed."
				::= { professionalWl5g 29 }				

	txPowerAdjustmentWl5g	OBJECT-TYPE
				SYNTAX INTEGER (0..200)
				MAX-ACCESS read-write
				STATUS current
				DESCRIPTION
					"Increase Tx Power to enhance the transmission quality or decrease Tx Power to reduce 
					power consumption."
				::= { professionalWl5g 30 }

-- ++++++++++++++++++++++++++++++++++++++++++++++++++++++++++++++++++++++
-- *  End of Professional Section (5G)
-- ++++++++++++++++++++++++++++++++++++++++++++++++++++++++++++++++++++++

-- **********************************************************************
-- *  End of 5G Section
-- **********************************************************************

-- ======================================================================
-- * End of Wireless Section
-- ======================================================================




-- ======================================================================
-- * LAN Section
-- ======================================================================

-- **********************************************************************
-- *  LAN IP Config Section 
-- **********************************************************************

	lan-ip			OBJECT IDENTIFIER ::= { lan 1 }

	lGetIpAutomatically	OBJECT-TYPE
				SYNTAX INTEGER { yes(1), no(2) }
				MAX-ACCESS read-write
				STATUS current
				DESCRIPTION ""
              	::= { lan-ip 1 }
	
	lIPAddress		OBJECT-TYPE
				SYNTAX IpAddress
				MAX-ACCESS read-write
				STATUS current
				DESCRIPTION
		        	"The value of this object is IP Address of the device as seen in your local network. 
					The default value is 192.168.1.1."
                ::= { lan-ip 2 }

	lSubnetMask		OBJECT-TYPE
				SYNTAX IpAddress
				MAX-ACCESS read-write
				STATUS current
				DESCRIPTION
					"The value this object is Subnet Mask of the device as seen in your local network. 
					The default value is 255.255.255.0."
				::= { lan-ip 3 }

	lDefaultGateway		OBJECT-TYPE
				SYNTAX IpAddress
				MAX-ACCESS read-write
				STATUS current
				DESCRIPTION ""
				::= { lan-ip 4 }

	lConnectToDnsServerAutomatically	OBJECT-TYPE
				SYNTAX INTEGER { yes(1), no(2) }
				MAX-ACCESS read-write
				STATUS current
				DESCRIPTION ""
                ::= { lan-ip 5 }

	lDnsServer1	OBJECT-TYPE
				SYNTAX OCTET STRING ( SIZE (0..15) )
				MAX-ACCESS read-write
				STATUS current
				DESCRIPTION ""
				::= { lan-ip 6 }

	lDnsServer2	OBJECT-TYPE
				SYNTAX OCTET STRING ( SIZE (0..15) )
				MAX-ACCESS read-write
				STATUS current
				DESCRIPTION ""
				::= { lan-ip 7 }

-- **********************************************************************
-- *  End of LAN IP Config Section 
-- **********************************************************************

-- **********************************************************************
-- *  DHCP server Config Section 
-- **********************************************************************

	dhcp-server		OBJECT IDENTIFIER ::= { lan 2 }

	basic-config-ds		OBJECT IDENTIFIER ::= { dhcp-server 1 }

	enableDHCPServer	OBJECT-TYPE
 				SYNTAX INTEGER { yes(1), no(2) }
				MAX-ACCESS read-write
                STATUS current
				DESCRIPTION
					"Enable the DHCP server function to allow the router's DHCP server to automatically assign 
					IP addresses to network clients. If this function is disabled, you need to manually assign 
					the IP address settings on your LAN devices."
				::= { basic-config-ds 1 }

	domainName	OBJECT-TYPE
                SYNTAX OCTET STRING ( SIZE (0..253) )
                MAX-ACCESS read-write
                STATUS current
                DESCRIPTION
					"The Domain Name for clients who request IP Address from the DHCP Server."
 				::= { basic-config-ds 2 }

	ipPoolStartingAddress	OBJECT-TYPE
				SYNTAX IpAddress
				MAX-ACCESS read-write
				STATUS current
				DESCRIPTION
					"The first address in the pool to be assigned by the DHCP server in LAN."
				::= { basic-config-ds 3 }

	ipPoolEndingAddress	OBJECT-TYPE
				SYNTAX IpAddress
				MAX-ACCESS read-write
				STATUS current
				DESCRIPTION
					"This field indicates the last address in the pool to be assigned by the DHCP server in LAN."
				::= { basic-config-ds 4 }

	leaseTime	OBJECT-TYPE
				SYNTAX INTEGER
				MAX-ACCESS read-write
				STATUS current
				DESCRIPTION
					"Set the lease time that the network client is allowed to use its current IP address to 
					connect to the wireless router. When the lease time expires, the network client should 
					either renew or get a new IP address from the wireless router's DHCP server."
				::= { basic-config-ds 5 }

	defaultGateway		OBJECT-TYPE
				SYNTAX OCTET STRING ( SIZE (0..15) )
				MAX-ACCESS read-write
				STATUS current
				DESCRIPTION
					"This field indicates the IP address of gateway in your LAN. If you leave it blank, the 
					IP address of RT-AC66U will be assigned."
				::= { basic-config-ds 6 }

	dns-wins-server		OBJECT IDENTIFIER ::= { dhcp-server 2 }

	dnsServer	OBJECT-TYPE
				SYNTAX OCTET STRING ( SIZE (0..15) )
				MAX-ACCESS read-write
				STATUS current
				DESCRIPTION
					"This field indicates the IP address of DNS to provide to clients that request IP Address 
					from DHCP Server. You can leave it blank, then the DNS request will be processed by RT-AC66U."
				::= { dns-wins-server 1 }

	winsServer	OBJECT-TYPE
				SYNTAX OCTET STRING ( SIZE (0..15) )
				MAX-ACCESS read-write
				STATUS current
				DESCRIPTION
					"The Windows Internet Naming Service manages interaction of each PC with the Internet. 
					If you use a WINS server, enter IP Address of server here."
				::= { dns-wins-server 2 }

	manual-assignment	OBJECT IDENTIFIER ::= { dhcp-server 3 }

	enableManualAssignment	OBJECT-TYPE
                SYNTAX INTEGER { yes(1), no(2) }
				MAX-ACCESS read-write
                STATUS current
				DESCRIPTION
					"Assign a fixed IP address for a specific client. The client's MAC address is required."
				::= { manual-assignment 1 }

	dsClientListAct		OBJECT-TYPE
				SYNTAX INTEGER { scan(1), nothing(2) }
				MAX-ACCESS read-write
				STATUS current
				DESCRIPTION ""
				::= { manual-assignment 2 }

	dsClientTable		OBJECT-TYPE
				SYNTAX SEQUENCE OF DsClientEntry
				MAX-ACCESS not-accessible
				STATUS current
				DESCRIPTION ""
                                ::= { manual-assignment 3 }

	dsClientEntry		OBJECT-TYPE
				SYNTAX DsClientEntry
				MAX-ACCESS not-accessible
				STATUS current
				DESCRIPTION ""
				INDEX { dsClientIndex }
				::= { dsClientTable 1 }

 	DsClientEntry ::= SEQUENCE {
        		dsClientIndex    	INTEGER,
        		dsClientMACAddr	    OCTET STRING,
				dsClientIPAddr	    IpAddress,
        		dsClientName		OCTET STRING
    	}

	dsClientIndex		OBJECT-TYPE
				SYNTAX INTEGER ( 1..32 )
				MAX-ACCESS not-accessible
				STATUS current
				DESCRIPTION
					"Client entry index."
				::= { dsClientEntry 1 }

	dsClientMACAddr		OBJECT-TYPE
				SYNTAX OCTET STRING
				MAX-ACCESS read-only
				STATUS current
				DESCRIPTION
					"MAC address of the client list."
				::= { dsClientEntry 2 }

	dsClientIPAddr		OBJECT-TYPE
				SYNTAX IpAddress
				MAX-ACCESS read-only
				STATUS current
				DESCRIPTION
					"IP address of the client list."
				::= { dsClientEntry 3 }

	dsClientName		OBJECT-TYPE
				SYNTAX OCTET STRING
				MAX-ACCESS read-only
				STATUS current
				DESCRIPTION
					"Name of the client list."
				::= { dsClientEntry 4 }

	assignedIPTable		OBJECT-TYPE
				SYNTAX SEQUENCE OF AssignedIPEntry
				MAX-ACCESS not-accessible
				STATUS current
				DESCRIPTION
					"Assigned IP around the DHCP list."
				::= { manual-assignment 4 }

	assignedIPEntry		OBJECT-TYPE
				SYNTAX AssignedIPEntry
				MAX-ACCESS not-accessible
				STATUS current
				DESCRIPTION ""
				INDEX { assignedIPIndex }
				::= { assignedIPTable 1 }

 	AssignedIPEntry ::= SEQUENCE {
        		assignedIPIndex		INTEGER,
        		assignedIPMACAddr	MacAddress,
				assignedIPIPAddr	IpAddress,
        		assignedIPDelEntry	INTEGER
    	}                           
    
	assignedIPIndex	OBJECT-TYPE
				SYNTAX INTEGER (1..64)
				MAX-ACCESS not-accessible
				STATUS current
				DESCRIPTION 
					"Remote AP Index."
				::= { assignedIPEntry 1 }

	assignedIPMACAddr	OBJECT-TYPE
				SYNTAX MacAddress
				MAX-ACCESS read-write
				STATUS current
				DESCRIPTION
					"MAC address of assigned IP around the DHCP list."
				::= { assignedIPEntry  2 }

	assignedIPIPAddr	OBJECT-TYPE
				SYNTAX IpAddress
				MAX-ACCESS read-write
				STATUS current
				DESCRIPTION
					"IP address of assigned IP around the DHCP list."
				::= { assignedIPEntry  3 }

	assignedIPDelEntry	OBJECT-TYPE
				SYNTAX INTEGER { yes(1), no(2) }
				MAX-ACCESS read-write
				STATUS current
				DESCRIPTION
					"Delete the assigned IP enntry."
				::= { assignedIPEntry 4 }

-- **********************************************************************
-- *  End of DHCP server Config Section 
-- **********************************************************************

-- **********************************************************************
-- *  Route Config Section 
-- **********************************************************************

	route		OBJECT IDENTIFIER ::= { lan 3 }

	enableStaticRoutes	OBJECT-TYPE
                SYNTAX INTEGER { yes(1), no(2) }
				MAX-ACCESS read-write
                STATUS current
				DESCRIPTION ""
				::= { route 1 }

	rClientListAct		OBJECT-TYPE
				SYNTAX INTEGER { scan(1), nothing(2) }
				MAX-ACCESS read-write
				STATUS current
				DESCRIPTION ""
				::= { route 2 }

	rClientTable		OBJECT-TYPE
				SYNTAX SEQUENCE OF RClientEntry
				MAX-ACCESS not-accessible
				STATUS current
				DESCRIPTION ""
                ::= { route 3 }

	rClientEntry		OBJECT-TYPE
				SYNTAX RClientEntry
				MAX-ACCESS not-accessible
				STATUS current
				DESCRIPTION ""
				INDEX { rClientIndex }
				::= { rClientTable 1 }

 	RClientEntry ::= SEQUENCE {
        		rClientIndex   	INTEGER,
        		rClientIPAddr	OCTET STRING,
        		rClientName		OCTET STRING
    	}

	rClientIndex	OBJECT-TYPE
				SYNTAX INTEGER ( 1..32 )
				MAX-ACCESS not-accessible
				STATUS current
				DESCRIPTION
					"Client entry index."
				::= { rClientEntry 1 }

	rClientIPAddr	OBJECT-TYPE
				SYNTAX OCTET STRING
				MAX-ACCESS read-only
				STATUS current
				DESCRIPTION
					"IP address of the client list."
				::= { rClientEntry 2 }

	rClientName		OBJECT-TYPE
				SYNTAX OCTET STRING
				MAX-ACCESS read-only
				STATUS current
				DESCRIPTION
					"Name of the client list."
				::= { rClientEntry 3 }

	staticRouteTable	OBJECT-TYPE
				SYNTAX SEQUENCE OF StaticRouteEntry
				MAX-ACCESS not-accessible
				STATUS current
				DESCRIPTION
					"Static route list."
				::= { route 4 }

	staticRouteEntry	OBJECT-TYPE
				SYNTAX StaticRouteEntry
				MAX-ACCESS not-accessible
				STATUS current
				DESCRIPTION ""
				INDEX { staticRouteIndex }
				::= { staticRouteTable 1 }

 	StaticRouteEntry ::= SEQUENCE {
        		staticRouteIndex		INTEGER,
	        	staticRouteIPAddr		OCTET STRING,
				staticRouteNetmask		IpAddress,
				staticRouteGateway		IpAddress,
				staticRouteMetric		INTEGER,
				staticRouteInterface	INTEGER,
        		staticRouteDelEntry		INTEGER
    }                           
    
	staticRouteIndex	OBJECT-TYPE
				SYNTAX INTEGER	( 1..32 )
				MAX-ACCESS not-accessible
				STATUS current
				DESCRIPTION 
					"Static Route Index."
				::= { staticRouteEntry 1 }

	staticRouteIPAddr	OBJECT-TYPE
				SYNTAX OCTET STRING
				MAX-ACCESS read-write
				STATUS current
				DESCRIPTION
					"IP address of static route list."
				::= { staticRouteEntry 2 }

	staticRouteNetmask	OBJECT-TYPE
				SYNTAX IpAddress
				MAX-ACCESS read-write
				STATUS current
				DESCRIPTION
					"Netmask of static route list."
				::= { staticRouteEntry 3 }

	staticRouteGateway	OBJECT-TYPE
				SYNTAX IpAddress
				MAX-ACCESS read-write
				STATUS current
				DESCRIPTION
					"Netmask of static route list."
				::= { staticRouteEntry 4 }

	staticRouteMetric	OBJECT-TYPE
				SYNTAX INTEGER
				MAX-ACCESS read-write
				STATUS current
				DESCRIPTION
					"Metric of static route list."
				::= { staticRouteEntry 5 }

	staticRouteInterface	OBJECT-TYPE
				SYNTAX INTEGER { lan(1), man(2), wan(3) }
				MAX-ACCESS read-write
				STATUS current
				DESCRIPTION
					"Interface of static route list."
				::= { staticRouteEntry 6 }

	staticRouteDelEntry	OBJECT-TYPE
				SYNTAX INTEGER { yes(1), no(2) }
				MAX-ACCESS read-write
				STATUS current
				DESCRIPTION
					"Delete the static route enntry."
				::= { staticRouteEntry 7 }


-- **********************************************************************
-- *  End of route Config Section 
-- **********************************************************************

-- **********************************************************************
-- *  IPTV Config Section 
-- **********************************************************************

	iptv		OBJECT IDENTIFIER ::= { lan 4 }

	port		OBJECT IDENTIFIER ::= { iptv 1 }

	selectISPProfile	OBJECT-TYPE
				SYNTAX INTEGER { none(1), unifi-home(2), unifi-business(3), singtel-mio(4), singtel-others(5), m1-fiber(6), maxis-fiber(7), maxis-fiber-special(8), manual(9) }
				MAX-ACCESS read-write
				STATUS current
				DESCRIPTION ""
				::= { port 1 }

	iptvSTBPort	OBJECT-TYPE
				SYNTAX INTEGER { none(1), lan1(2), lan2(3), lan3(4), lan4(5), lan1-and-lan2(6), lan3-and-lan4(7) }
				MAX-ACCESS read-write
				STATUS current
				DESCRIPTION 
					"This variable can be set only when the value of 'selectISPProfile' is 'none'."
				::= { port 2 }

	voipPort	OBJECT-TYPE
                SYNTAX OCTET STRING
                MAX-ACCESS read-only
                STATUS current
                DESCRIPTION ""
                ::= { port 3 }
	
	internetVID	OBJECT-TYPE
				SYNTAX OCTET STRING
				MAX-ACCESS read-write
				STATUS current
				DESCRIPTION 
					"User can set this variable only when 'selectISPProfile' is 'manual'. 
					 Blank value means internetVID won't be used. Value Range: 2-4094."
				::= { port 4 }

	internetPRIO	OBJECT-TYPE
				SYNTAX INTEGER ( 0..7 )
				MAX-ACCESS read-write
				STATUS current
				DESCRIPTION 
					"User can set this variable only when 'selectISPProfile' is 'manual'. "
				::= { port 5 }

	lan4PortVID	OBJECT-TYPE
				SYNTAX OCTET STRING
				MAX-ACCESS read-write
				STATUS current
				DESCRIPTION 
					"User can set this variable only when 'selectISPProfil'e is 'manual'. 
					 Blank value means internetVID won't be used. Value Range: 2-4094."
				::= { port 6 }

	lan4PortPRIO	OBJECT-TYPE
				SYNTAX INTEGER ( 0..7 )
				MAX-ACCESS read-write
				STATUS current
				DESCRIPTION 
					"User can set this variable only when 'selectISPProfile' is 'manual'. "
				::= { port 7 }
				
	lan3PortVID		OBJECT-TYPE
				SYNTAX OCTET STRING
				MAX-ACCESS read-write
				STATUS current
				DESCRIPTION 
					"User can set this variable only when 'selectISPProfile' is 'manual'. 
					 Blank value means internetVID won't be used. Value Range: 2-4094."
				::= { port 8 }

	lan3PortPRIO	OBJECT-TYPE
				SYNTAX INTEGER ( 0..7 )
				MAX-ACCESS read-write
				STATUS current
				DESCRIPTION 
					"User can set this variable only when 'selectISPProfile' is 'manual'. "
				::= { port 9 }

	special-applications	OBJECT IDENTIFIER ::= { iptv 2 }

	useDHCPRoutes	OBJECT-TYPE
				SYNTAX INTEGER { disable(1), microsoft(2), rfc3442(3), rfc3442-and-microsoft(4) }
				MAX-ACCESS read-write
				STATUS current
				DESCRIPTION ""
				::= { special-applications 1 }

	enableMulticastRouting	OBJECT-TYPE
                SYNTAX INTEGER { enable(1), disable(2) }
				MAX-ACCESS read-write
				STATUS current                                                        
                DESCRIPTION
					"Allows the wireless router to handle the multicast packets. Enabling multicast router 
					also enables the RTP and RTSP functions."
                                ::= { special-applications 2 }

	enableEfficientMulticastForwarding	OBJECT-TYPE
                SYNTAX INTEGER { enable(1), disable(2) }
				MAX-ACCESS read-write
				STATUS current                                                        
                DESCRIPTION ""
                ::= { special-applications 3 }

	udpProxy	OBJECT-TYPE
				SYNTAX INTEGER
				MAX-ACCESS read-write
				STATUS current
				DESCRIPTION
					"Use this function to run the IPTV application (such as VLC) on several computers at the 
					same time. This function can convert multicast UDP streams to unicast HTTP streams. Enter 
					the port (such as 4000) that you want to assign for the IPTV application, then use this 
					format to enter the address in the play list to watch IPTV streams: http://[Router IP]:
					[Udpxy port]/[protocol]/[channel IP address]:[channel  port] (such as http://192.168.1.1:
					4000/udp/239.255.1.1:5000 or http://192.168.1.1:4000/rtp/239.255.1.2:5000). Enter 0 (zero) 
					to disable this function."
				::= { special-applications 4 }

-- **********************************************************************
-- *  End of IPTV Config Section 
-- **********************************************************************


-- **********************************************************************
-- *  Switch Control Config Section 
-- **********************************************************************

	switch-control		OBJECT IDENTIFIER ::= { lan 5 }

	enableJumboFrame	OBJECT-TYPE
                SYNTAX INTEGER { enable(1), disable(2) }
				MAX-ACCESS read-write
                STATUS current
				DESCRIPTION ""
				::= { switch-control 1 }

	enableNATAccelerator	OBJECT-TYPE
                SYNTAX INTEGER { enable(1), disable(2) }
				MAX-ACCESS read-write
                STATUS current
				DESCRIPTION ""
				::= { switch-control 2 }


-- **********************************************************************
-- *  End of Switch Control Config Section 
-- **********************************************************************

-- ======================================================================
-- * End of LAN Section
-- ======================================================================





-- ======================================================================
-- * WAN Section
-- ======================================================================

-- **********************************************************************
-- *  Internet Connection Config Section 
-- **********************************************************************
	internet-connection	OBJECT IDENTIFIER ::= { wan 1 }
                                                                                                                                                                                                                                                                          
    wantype-wan	OBJECT IDENTIFIER ::= { internet-connection 1 }                                                                   
	
	wbasic-config-ic	OBJECT IDENTIFIER ::= { wantype-wan 1 }

	wwanConnectionType	OBJECT-TYPE
				SYNTAX INTEGER { automatic-ip(1), pppoe(2), static-ip(3), pptp(4), l2tp(5) }
				MAX-ACCESS read-write
				STATUS current
				DESCRIPTION ""
				::= { wbasic-config-ic 1 }

	wenableWAN	OBJECT-TYPE
				SYNTAX INTEGER { yes(1), no(2) }
				MAX-ACCESS read-write
				STATUS current
				DESCRIPTION ""
				::= { wbasic-config-ic 2 }

	wenableNAT	OBJECT-TYPE
				SYNTAX INTEGER { yes(1), no(2) }
				MAX-ACCESS read-write
				STATUS current
				DESCRIPTION
					"NAT (Network Address Translation) is a process used in routers to replace the address 
					information of network packet with new address information. Typical applications for NAT 
					is router which connect to LAN with the WAN. In LAN every network devices had a private 
					IP(LAN IP) but there is only one public IP(WAN IP). To grant the network devices access 
					to the Internet, the router replaces the private IP address of the sender with its own 
					public IP address in all outgoing data packets. The router saves all necessary information 
					in a table(NAT table) so that incoming data packets can then be assigned on the correct 
					network device."
				::= { wbasic-config-ic 3 }

	wenableUPnP	OBJECT-TYPE
				SYNTAX INTEGER { yes(1), no(2) }
				MAX-ACCESS read-write
				STATUS current
				DESCRIPTION
					"UPnP (Universal Plug and Play) allows several devices (routers, televisions, stereo 
					systems, game consoles, cellular phone) to be controlled via an IP-based network with or 
					without a central control through a gateway."
				::= { wbasic-config-ic 4 }

	wwan-ip-setting		OBJECT IDENTIFIER ::= { wantype-wan 2 }

	wgetWanIPAuto	OBJECT-TYPE
				SYNTAX INTEGER { yes(1), no(2) }
				MAX-ACCESS read-write
				STATUS current
				DESCRIPTION ""
				::= { wwan-ip-setting 1 }

	wwIPAddress	OBJECT-TYPE
				SYNTAX IpAddress
				MAX-ACCESS read-write
				STATUS current
				DESCRIPTION
		        	"If your WAN connection requires a static IP address, key in the IP address in this field."
                ::= { wwan-ip-setting 2 }

	wwSubnetMask	OBJECT-TYPE
				SYNTAX IpAddress
				MAX-ACCESS read-write
				STATUS current
				DESCRIPTION
					"If your WAN connection requires a static IP address, key in the subnet mask in this field."
				::= { wwan-ip-setting 3 }

	wwDefaultGateway	OBJECT-TYPE
				SYNTAX IpAddress
				MAX-ACCESS read-write
				STATUS current
				DESCRIPTION
					"If your WAN connection requires a static IP address, key in the gateway IP address in this 
					field."
				::= { wwan-ip-setting 4 }

	wwan-dns-setting	OBJECT IDENTIFIER ::= { wantype-wan 3 }

	wconnectDNSServerAuto	OBJECT-TYPE
				SYNTAX INTEGER { yes(1), no(2) }
				MAX-ACCESS read-write
				STATUS current
				DESCRIPTION
					"Allows this router to get the DNS IP address from the ISP automatically."
				::= { wwan-dns-setting 1 }

	wdnsServer1	OBJECT-TYPE
                SYNTAX OCTET STRING ( SIZE (0..15) )
                MAX-ACCESS read-write
                STATUS current
                DESCRIPTION
					"This field indicates the IP address of DNS that RT-AC66U contact to."
                ::= { wwan-dns-setting 2 }

	wdnsServer2	OBJECT-TYPE
                SYNTAX OCTET STRING ( SIZE (0..15) )
                MAX-ACCESS read-write
                STATUS current
                DESCRIPTION
					"This field indicates the IP address of DNS that RT-AC66U contact to."
                ::= { wwan-dns-setting 3 }

	waccount-setting		OBJECT IDENTIFIER ::= { wantype-wan 4 }

	wAuthentication		OBJECT-TYPE
				SYNTAX INTEGER { none(1), dot1x-md5(2) }
				MAX-ACCESS read-write
				STATUS current
				DESCRIPTION ""
				::= { waccount-setting 1 }

	wUserName	OBJECT-TYPE
                SYNTAX OCTET STRING ( SIZE (1..64) )
                MAX-ACCESS read-write
                STATUS current
                DESCRIPTION
					"This field is only available when you set the WAN Connection Type as USB Modem, PPPoE, 
					PPTP or L2TP."
                ::= { waccount-setting 2 }

	wPassword	OBJECT-TYPE
                SYNTAX OCTET STRING ( SIZE (1..64) )
                MAX-ACCESS read-write
                STATUS current
                DESCRIPTION
					"This field is only available when you set WAN Connection Type as PPPoE."
                ::= { waccount-setting 3 }

	widleDisconnectTime	OBJECT-TYPE
				SYNTAX INTEGER
				MAX-ACCESS read-write
				STATUS current
				DESCRIPTION
					"This field is optional and allows you to configure to terminate your ISP connection after 
					a specified period of time. A value of zero allows infinite idle time."
				::= { waccount-setting 4 }

	wmtu		OBJECT-TYPE
				SYNTAX INTEGER
				MAX-ACCESS read-write
				STATUS current
				DESCRIPTION
					"The Maximum Transmission Unit (MTU) of PPPoE packet. The default value is 1492. Change this 
					value only if your ISP requires it."
				::= { waccount-setting 5 }

	wmru		OBJECT-TYPE
				SYNTAX INTEGER
				MAX-ACCESS read-write
				STATUS current
				DESCRIPTION
					"The Maximum Receive Unit (MRU) of PPPoE packet. The default value is 1492. Change this value 
					only if your ISP requires it."
				::= { waccount-setting 6 }

	wserviceName	OBJECT-TYPE
                SYNTAX OCTET STRING ( SIZE (1..32) )
                MAX-ACCESS read-write
                STATUS current
                DESCRIPTION
					"This field is optional and may be specified by some ISPs. Check with your ISP and fill them 
					in if required."
                ::= { waccount-setting 7 }

	waccessConcentratorName		OBJECT-TYPE
                SYNTAX OCTET STRING ( SIZE (1..32) )
                MAX-ACCESS read-write
                STATUS current
                DESCRIPTION
					"This field is optional and may be specified by some ISPs. Check with your ISP and fill them 
					in if required."
                ::= { waccount-setting 8 }

	wpptpOptions	OBJECT-TYPE
				SYNTAX INTEGER { auto(1), no-encryption(2), mppe-40(3), mppe-128(4) }
				MAX-ACCESS read-write
				STATUS current
				DESCRIPTION
					"This field is optional and may be specified by some ISPs. Check with your ISP and fill them 
					in if required."
				::= { waccount-setting 9 }

	wadditionalPppdOptions		OBJECT-TYPE
                SYNTAX OCTET STRING ( SIZE (1..32) )
                MAX-ACCESS read-write
                STATUS current
                DESCRIPTION
					"This field is optional and may be specified by some ISPs. Check with your ISP and fill them 
					in if required."
                ::= { waccount-setting 10 }

	wspecial-requirement-from-ISP	OBJECT IDENTIFIER ::= { wantype-wan 5 }

	wvpnServer	OBJECT-TYPE
                SYNTAX OCTET STRING ( SIZE (1..256) )
                MAX-ACCESS read-write
                STATUS current
                DESCRIPTION
					"If your WAN connection type is PPTP or L2TP, Please enter the server name or server ip of the 
					VPN server."
                ::= { wspecial-requirement-from-ISP 1 }

	wenableVPNandDHCPConnection		OBJECT-TYPE
				SYNTAX INTEGER { yes(1), no(2) }
				MAX-ACCESS read-write
				STATUS current
				DESCRIPTION ""
				::= { wspecial-requirement-from-ISP 2 }

	wHostName	OBJECT-TYPE
                SYNTAX OCTET STRING ( SIZE (1..32) )
                MAX-ACCESS read-write
                STATUS current
                DESCRIPTION
					"This field allows you to provide a host name for RT-AC66U. It is usually requested by your ISP."
                ::= { wspecial-requirement-from-ISP 3 }

	wMacAddress	OBJECT-TYPE
				SYNTAX MacAddress
				MAX-ACCESS read-write
				STATUS current
				DESCRIPTION
					"MAC (Media Access Control) address is a unique identifier that identifies your computer or 
					device in the network. ISPs monitor the MAC addresses of devices that connect to their services, 
					and would disallow Internet connection for new MAC addresses. To fix this issue, you can do 
					either of the following: *Contact your ISP and request to update the MAC address associated 
					with your ISP subscription. *Clone or change the MAC address of the new device to match the 
					MAC address of the original device."
				::= { wspecial-requirement-from-ISP  4 }

	wdhcpQueryFrequency	OBJECT-TYPE
				SYNTAX INTEGER { normal-mode(1), aggressive-mode(2) }
				MAX-ACCESS read-write
				STATUS current
				DESCRIPTION ""
				::= { wspecial-requirement-from-ISP 5 }
                                                           
	wantype-lan	OBJECT IDENTIFIER ::= { internet-connection 2 }                                                                   
	
	lbasic-config-ic	OBJECT IDENTIFIER ::= { wantype-lan 1 }

	lwanConnectionType	OBJECT-TYPE
				SYNTAX INTEGER { automatic-ip(1), pppoe(2), static-ip(3), pptp(4), l2tp(5) }
				MAX-ACCESS read-write
				STATUS current
				DESCRIPTION ""
				::= { lbasic-config-ic 1 }

	lenableWAN	OBJECT-TYPE
				SYNTAX INTEGER { yes(1), no(2) }
				MAX-ACCESS read-write
				STATUS current
				DESCRIPTION ""
				::= { lbasic-config-ic 2 }

	lenableNAT	OBJECT-TYPE
				SYNTAX INTEGER { yes(1), no(2) }
				MAX-ACCESS read-write
				STATUS current
				DESCRIPTION
					"NAT (Network Address Translation) is a process used in routers to replace the address 
					information of network packet with new address information. Typical applications for NAT 
					is router which connect to LAN with the WAN. In LAN every network devices had a private 
					IP(LAN IP) but there is only one public IP(WAN IP). To grant the network devices access 
					to the Internet, the router replaces the private IP address of the sender with its own 
					public IP address in all outgoing data packets. The router saves all necessary information 
					in a table(NAT table) so that incoming data packets can then be assigned on the correct 
					network device."
				::= { lbasic-config-ic 3 }

	lenableUPnP	OBJECT-TYPE
				SYNTAX INTEGER { yes(1), no(2) }
				MAX-ACCESS read-write
				STATUS current
				DESCRIPTION
					"UPnP (Universal Plug and Play) allows several devices (routers, televisions, stereo 
					systems, game consoles, cellular phone) to be controlled via an IP-based network with or 
					without a central control through a gateway."
				::= { lbasic-config-ic 4 }

	lwan-ip-setting		OBJECT IDENTIFIER ::= { wantype-lan 2 }

	lgetWanIPAuto	OBJECT-TYPE
				SYNTAX INTEGER { yes(1), no(2) }
				MAX-ACCESS read-write
				STATUS current
				DESCRIPTION ""
				::= { lwan-ip-setting 1 }

	lwIPAddress	OBJECT-TYPE
				SYNTAX IpAddress
				MAX-ACCESS read-write
				STATUS current
				DESCRIPTION
		        	"If your WAN connection requires a static IP address, key in the IP address in this field."
                ::= { lwan-ip-setting 2 }

	lwSubnetMask		OBJECT-TYPE
				SYNTAX IpAddress
				MAX-ACCESS read-write
				STATUS current
				DESCRIPTION
					"If your WAN connection requires a static IP address, key in the subnet mask in this field."
				::= { lwan-ip-setting 3 }

	lwDefaultGateway	OBJECT-TYPE
				SYNTAX IpAddress
				MAX-ACCESS read-write
				STATUS current
				DESCRIPTION
					"If your WAN connection requires a static IP address, key in the gateway IP address in this 
					field."
				::= { lwan-ip-setting 4 }

	lwan-dns-setting		OBJECT IDENTIFIER ::= { wantype-lan 3 }

	lwconnectDNSServerAuto	OBJECT-TYPE
				SYNTAX INTEGER { yes(1), no(2) }
				MAX-ACCESS read-write
				STATUS current
				DESCRIPTION
					"Allows this router to get the DNS IP address from the ISP automatically."
				::= { lwan-dns-setting 1 }

	lwdnsServer1	OBJECT-TYPE
                SYNTAX OCTET STRING ( SIZE (0..15) )
                MAX-ACCESS read-write
                STATUS current
                DESCRIPTION
					"This field indicates the IP address of DNS that RT-AC66U contact to."
                ::= { lwan-dns-setting 2 }

	lwdnsServer2	OBJECT-TYPE
                SYNTAX OCTET STRING ( SIZE (0..15) )
                MAX-ACCESS read-write
                STATUS current
                DESCRIPTION
					"This field indicates the IP address of DNS that RT-AC66U contact to."
                ::= { lwan-dns-setting 3 }

	laccount-setting	OBJECT IDENTIFIER ::= { wantype-lan 4 }

	lAuthentication		OBJECT-TYPE
				SYNTAX INTEGER { none(1), dot1x-md5(2) }
				MAX-ACCESS read-write
				STATUS current
				DESCRIPTION ""
				::= { laccount-setting 1 }

	lUserName	OBJECT-TYPE
                SYNTAX OCTET STRING ( SIZE (1..64) )
                MAX-ACCESS read-write
                STATUS current
                DESCRIPTION
					"This field is only available when you set the WAN Connection Type as USB Modem, PPPoE, 
					PPTP or L2TP."
                ::= { laccount-setting 2 }

	lPassword	OBJECT-TYPE
                SYNTAX OCTET STRING ( SIZE (1..64) )
                MAX-ACCESS read-write
                STATUS current
                DESCRIPTION
					"This field is only available when you set WAN Connection Type as PPPoE."
                ::= { laccount-setting 3 }

	lidleDisconnectTime	OBJECT-TYPE
				SYNTAX INTEGER
				MAX-ACCESS read-write
				STATUS current
				DESCRIPTION
					"This field is optional and allows you to configure to terminate your ISP connection after 
					a specified period of time. A value of zero allows infinite idle time."
				::= { laccount-setting 4 }

	lmtu		OBJECT-TYPE
				SYNTAX INTEGER
				MAX-ACCESS read-write
				STATUS current
				DESCRIPTION
					"The Maximum Transmission Unit (MTU) of PPPoE packet. The default value is 1492. Change this 
					value only if your ISP requires it."
				::= { laccount-setting 5 }

	lmru		OBJECT-TYPE
				SYNTAX INTEGER
				MAX-ACCESS read-write
				STATUS current
				DESCRIPTION
					"The Maximum Receive Unit (MRU) of PPPoE packet. The default value is 1492. Change this value 
					only if your ISP requires it."
				::= { laccount-setting 6 }

	lserviceName		OBJECT-TYPE
                SYNTAX OCTET STRING ( SIZE (1..32) )
                MAX-ACCESS read-write
                STATUS current
                DESCRIPTION
					"This field is optional and may be specified by some ISPs. Check with your ISP and fill them 
					in if required."
                ::= { laccount-setting 7 }

	laccessConcentratorName		OBJECT-TYPE
                SYNTAX OCTET STRING ( SIZE (1..32) )
                MAX-ACCESS read-write
                STATUS current
                DESCRIPTION
					"This field is optional and may be specified by some ISPs. Check with your ISP and fill them 
					in if required."
                ::= { laccount-setting 8 }

	lpptpOptions	OBJECT-TYPE
				SYNTAX INTEGER { auto(1), no-encryption(2), mppe-40(3), mppe-128(4) }
				MAX-ACCESS read-write
				STATUS current
				DESCRIPTION
					"This field is optional and may be specified by some ISPs. Check with your ISP and fill them 
					in if required."
				::= { laccount-setting 9 }

	ladditionalPppdOptions		OBJECT-TYPE
                SYNTAX OCTET STRING ( SIZE (1..32) )
                MAX-ACCESS read-write
                STATUS current
                DESCRIPTION
					"This field is optional and may be specified by some ISPs. Check with your ISP and fill them 
					in if required."
                ::= { laccount-setting 10 }

	lspecial-requirement-from-ISP	OBJECT IDENTIFIER ::= { wantype-lan 5 }

	lvpnServer	OBJECT-TYPE
                SYNTAX OCTET STRING ( SIZE (1..256) )
                MAX-ACCESS read-write
                STATUS current
                DESCRIPTION
					"If your WAN connection type is PPTP or L2TP, Please enter the server name or server ip of the 
					VPN server."
                ::= { lspecial-requirement-from-ISP 1 }

	lenableVPNandDHCPConnection		OBJECT-TYPE
				SYNTAX INTEGER { yes(1), no(2) }
				MAX-ACCESS read-write
				STATUS current
				DESCRIPTION ""
				::= { lspecial-requirement-from-ISP 2 }

	lHostName	OBJECT-TYPE
                SYNTAX OCTET STRING ( SIZE (1..32) )
                MAX-ACCESS read-write
                STATUS current
                DESCRIPTION
					"This field allows you to provide a host name for RT-AC66U. It is usually requested by your ISP."
                ::= { lspecial-requirement-from-ISP 3 }

	lMacAddress	OBJECT-TYPE
				SYNTAX MacAddress
				MAX-ACCESS read-write
				STATUS current
				DESCRIPTION
					"MAC (Media Access Control) address is a unique identifier that identifies your computer or 
					device in the network. ISPs monitor the MAC addresses of devices that connect to their services, 
					and would disallow Internet connection for new MAC addresses. To fix this issue, you can do 
					either of the following: *Contact your ISP and request to update the MAC address associated 
					with your ISP subscription. *Clone or change the MAC address of the new device to match the 
					MAC address of the original device."
				::= { lspecial-requirement-from-ISP  4 }

	ldhcpQueryFrequency	OBJECT-TYPE
				SYNTAX INTEGER { normal-mode(1), aggressive-mode(2) }
				MAX-ACCESS read-write
				STATUS current
				DESCRIPTION ""
				::= { lspecial-requirement-from-ISP 5 }
 
 	wantype-usb	OBJECT IDENTIFIER ::= { internet-connection 3 }                                                           
 	   
 	uEnableUSBModem	OBJECT-TYPE
				SYNTAX INTEGER { yes(1), no(0) }
				MAX-ACCESS read-write
				STATUS current
				DESCRIPTION ""
				::= { wantype-usb 1 } 
								
    uUsbModem	OBJECT-TYPE
				SYNTAX INTEGER { wcdma(1), cdma2000(2), td-scdma(3), wimax(4) }
				MAX-ACCESS read-write
				STATUS current
				DESCRIPTION ""
				::= { wantype-usb 2 }  
   				
  	uNetworkType	OBJECT-TYPE
				SYNTAX INTEGER { auto(1), both4g-3g(2), only4g(3), only3g(4), only2g(5) }
				MAX-ACCESS read-write
				STATUS current
				DESCRIPTION ""
				::= { wantype-usb 3 }    
				
	uAPNService OBJECT-TYPE
                SYNTAX OCTET STRING
                MAX-ACCESS read-write
                STATUS current
                DESCRIPTION
					"This is optional. If you do not know the APN service name, please contact your ISP."
                ::= { wantype-usb 4 }		
                
	uDialNumber OBJECT-TYPE
                SYNTAX OCTET STRING
                MAX-ACCESS read-write
                STATUS current
                DESCRIPTION
					"Please enter your dial number."
                ::= { wantype-usb 5 }           		
 	
 	uPinCode	OBJECT-TYPE
                SYNTAX OCTET STRING
                MAX-ACCESS read-write
                STATUS current
                DESCRIPTION
					"Please input the Personal Identification Number(PIN) code of your SIM card. 
					It must be the number which length is greater than 4 and smaller than 8. If 
					you do not know the PIN code, please contact your ISP."
                ::= { wantype-usb 6 }    
                
    uUsername   OBJECT-TYPE
                SYNTAX OCTET STRING
                MAX-ACCESS read-write
                STATUS current
                DESCRIPTION
					"Please enter your username."
                ::= { wantype-usb 7 }          
                
    uPassword   OBJECT-TYPE
                SYNTAX OCTET STRING
                MAX-ACCESS read-write
                STATUS current
                DESCRIPTION
					"Please enter your password."
                ::= { wantype-usb 8 }   

    uEmail		OBJECT-TYPE
                SYNTAX OCTET STRING
                MAX-ACCESS read-write
                STATUS current
                DESCRIPTION ""
                ::= { wantype-usb 9 }  
                                
	uUSBAdapter	OBJECT-TYPE
				SYNTAX INTEGER	{ auto(0), samsung-u200(1), asus-t500(2), bandluxe-c120(3), bandluxe-c170(4), bandluxe-c339(5), 
								huawei-e1550(6), huawei-e160g(7),huawei-e161(8), huawei-e169(9), huawei-e176(10), 
								huawei-e220(11), huawei-k3520(12), huawei-et128(13), huawei-e1800(14), 
								huawei-k4505(15), huawei-e172(16), huawei-e372(17), huawei-e122(18), 
								huawei-e160e(19), huawei-e1552(20), huawei-e173(21), huawei-e1823(22), 
								huawei-e1762(23), huawei-e1750c(24), huawei-e1752cu(25), alcatel-x200(26), 
								alcatel-oune-touch-x220s(27), anydata-adu-510a(28), anydata-adu-500a(29), 
								onda-mt833up(30), onda-mw833up(31), mts-ac2746(32), zte-ac5710(33), zte-mu351(34),
								zte-mf100(35), zte-mf636(36), zte-mf622(37), zte-mf626(38), zte-mf632(39), 
								zte-mf112(40), zte-mfk3570-z(41), cs15(42), cs17(43), icon401(44) }
				MAX-ACCESS read-write
				STATUS current
				DESCRIPTION ""
				::= { wantype-usb 10 }            
				
-- **********************************************************************
-- *  End of Internet Connection Config Section 
-- **********************************************************************
    
-- **********************************************************************
-- *  Dual WAN Section 
-- **********************************************************************
  	dual-wan		OBJECT IDENTIFIER ::= { wan 2 } 
  	
  	dwbasic-config	OBJECT IDENTIFIER ::= { dual-wan 1 }    
  	                                                       
	dwPrimaryWAN	OBJECT-TYPE
					SYNTAX INTEGER { wan(1), usb(2), lan(3) }
					MAX-ACCESS read-write
					STATUS current
					DESCRIPTION	"Primary WAN and secondary wan must be different. "
					::= { dwbasic-config 1 } 
					
	dwPWLanPort		OBJECT-TYPE
					SYNTAX INTEGER { lan1(1), lan2(2), lan3(3), lan4(4) }
					MAX-ACCESS read-write
					STATUS current
					DESCRIPTION	""
					::= { dwbasic-config 2 }			
                                                       
   	dwSecondaryWAN	OBJECT-TYPE
					SYNTAX INTEGER { none(0), wan(1), usb(2), lan(3) }
					MAX-ACCESS read-write
					STATUS current
					DESCRIPTION	"Value 'none' means there is no secondary WAN. And primary 
								WAN and secondary wan must be different."
					::= { dwbasic-config 3 }
                                                 
	dwSWLanPort		OBJECT-TYPE
					SYNTAX INTEGER { lan1(1), lan2(2), lan3(3), lan4(4) }
					MAX-ACCESS read-write
					STATUS current
					DESCRIPTION	""
					::= { dwbasic-config 4 }                                            
                                                 
	dwDualWANMode	OBJECT-TYPE
					SYNTAX INTEGER { fail-over(1), load-balance(2) }
					MAX-ACCESS read-write
					STATUS current
					DESCRIPTION	
						"Load Balance optimizes resource use and maximizes throughput. 
						Use Failover mode for better performance if the difference of 
						bandwidth between the Primary and Secondary WAN is more than 10Mbps."
					::= { dwbasic-config 5 }
                                             
	dwLoadBalanceCfgPri  OBJECT-TYPE
					SYNTAX INTEGER ( 1..9 )
					MAX-ACCESS read-write
					STATUS current
					DESCRIPTION	""
					::= { dwbasic-config 6 }

	dwLoadBalanceCfgSec  OBJECT-TYPE
					SYNTAX INTEGER ( 1..9 )
					MAX-ACCESS read-write
					STATUS current
					DESCRIPTION	""
					::= { dwbasic-config 7 }   
					
	dwAllowFailBack	OBJECT-TYPE
					SYNTAX INTEGER { yes(1), no(2) }
					MAX-ACCESS read-write
					STATUS current
					DESCRIPTION ""
					::= { dwbasic-config  8 }   	
					                		
	dwPingTimeWatchdog	OBJECT IDENTIFIER ::= { dual-wan  2 }       
	
	dwPingInterval  OBJECT-TYPE
					SYNTAX INTEGER ( 1..9 )
					MAX-ACCESS read-write
					STATUS current
					DESCRIPTION	
						"Time interval between two ping packets."
					::= { dwPingTimeWatchdog 1 }   
  
  	dwPingDelay		OBJECT-TYPE
					SYNTAX INTEGER ( 1..99 )
					MAX-ACCESS read-write
					STATUS current
					DESCRIPTION	
						"Time delay before the first ping packet is sent out when the router is restarted."
					::= { dwPingTimeWatchdog 2 }    
					
  	dwPingFailCount	OBJECT-TYPE
					SYNTAX INTEGER ( 1..99 )
					MAX-ACCESS read-write
					STATUS current
					DESCRIPTION	
						"Maximum number of pings the router sends continuously. If this value is reached, 
						 the primary WAN connection will be switched to the secondary WAN."
					::= { dwPingTimeWatchdog 3 } 	
					
  	dwPingFbCount	OBJECT-TYPE
					SYNTAX INTEGER ( 1..99 )
					MAX-ACCESS read-write
					STATUS current
					DESCRIPTION	
						"Once switched to secondary wan, firmware can still detect the primary wan. 
						 When primary wan keep IP over the set value (Interval+delay)*failback count, 
						 the connection switched back to primary wan."
					::= { dwPingTimeWatchdog 4 } 
				                                            
    dwPingEnableWatchdog OBJECT-TYPE
					SYNTAX INTEGER { yes(1), no(2) }
					MAX-ACCESS read-write
					STATUS current
					DESCRIPTION 
						"You can enable Ping Time Watchdog to continuously monitor the primary WAN 
						 connection between ZVMODELVZ and the remote host. The router will continuously 
						 ping a user defined target in this setting. If the router fails to ping the 
						target IP address, the rouer will automatically do a failover."
					::= { dwPingTimeWatchdog  5 }  

	dwPingTarget	OBJECT-TYPE
                	SYNTAX OCTET STRING
                	MAX-ACCESS read-write
                	STATUS current
                	DESCRIPTION
						"The IP address of the target host where the router is sending ping packets continuously."
                ::= { dwPingTimeWatchdog  6 }					 
	
	dwRoutingRules	OBJECT IDENTIFIER ::= { dual-wan  3 } 	
			                   	 			                   
    dwEnableRoutingRules OBJECT-TYPE
					SYNTAX INTEGER { yes(1), no(2) }
					MAX-ACCESS read-write
					STATUS current
					DESCRIPTION ""
					::= { dwRoutingRules  1 }
					
	dwRoutingRulesTable	OBJECT-TYPE
				SYNTAX SEQUENCE OF DwRoutingRuleEntry
				MAX-ACCESS not-accessible
				STATUS current
				DESCRIPTION
					"Routing Rules."
				::= { dwRoutingRules 2 }

	dwRoutingRule	OBJECT-TYPE
				SYNTAX DwRoutingRuleEntry
				MAX-ACCESS not-accessible
				STATUS current
				DESCRIPTION ""
				INDEX { dwRoutingRuleIndex }
				::= { dwRoutingRulesTable 1 }

 	DwRoutingRuleEntry ::= SEQUENCE {
        		dwRoutingRuleIndex		INTEGER,
				dwSourceIP				IpAddress,
				dwDestinationIP			IpAddress,
				dwWANUnit				INTEGER,
        		dwRoutingRuleDelEntry	INTEGER
    		}                           
                                                              
	dwRoutingRuleIndex	OBJECT-TYPE
				SYNTAX INTEGER  ( 1..32 )
				MAX-ACCESS not-accessible
				STATUS current
				DESCRIPTION 
					"Routing Rule index."
				::= { dwRoutingRule 1 }     
				
	dwSourceIP	OBJECT-TYPE
				SYNTAX IpAddress
				MAX-ACCESS read-write
				STATUS current
				DESCRIPTION
					"Source IP address of the routing rule."
				::= { dwRoutingRule 2 }
				                                   
	dwDestinationIP	OBJECT-TYPE
				SYNTAX IpAddress
				MAX-ACCESS read-write
				STATUS current
				DESCRIPTION
					"Destination IP address of the routing rule."
				::= { dwRoutingRule 3 }
				                                   
   	dwWANUnit	OBJECT-TYPE
				SYNTAX INTEGER { primary-wan(1), secondary-wan(2) }
				MAX-ACCESS read-write
				STATUS current
				DESCRIPTION ""
				::= { dwRoutingRule 4 }   
				
	dwRoutingRuleDelEntry	OBJECT-TYPE
				SYNTAX INTEGER { yes(1), no(2) }
				MAX-ACCESS read-write
				STATUS current
				DESCRIPTION
					"Delete the routing rule enntry."
				::= { dwRoutingRule 5 }
				
				                             
-- **********************************************************************
-- *  End of Dual WAN Section 
-- **********************************************************************
                                             
-- **********************************************************************
-- *  Port Trigger Config Section 
-- **********************************************************************

	port-trigger		OBJECT IDENTIFIER ::= { wan 3 }

	enablePortTrigger	OBJECT-TYPE
				SYNTAX INTEGER { yes(1), no(2) }
				MAX-ACCESS read-write
				STATUS current
				DESCRIPTION ""
				::= { port-trigger 1 }

	portTriggerTable	OBJECT-TYPE
				SYNTAX SEQUENCE OF PortTriggerEntry
				MAX-ACCESS not-accessible
				STATUS current
				DESCRIPTION
					"Prt tirgger list."
				::= { port-trigger 2 }

	portTriggerEntry	OBJECT-TYPE
				SYNTAX PortTriggerEntry
				MAX-ACCESS not-accessible
				STATUS current
				DESCRIPTION ""
				INDEX { portTriggerIndex }
				::= { portTriggerTable 1 }

 	PortTriggerEntry ::= SEQUENCE {
        		portTriggerIndex			INTEGER,
				portTriggerDescription		OCTET STRING,
				portTriggerPort				OCTET STRING,
				portTriggerProtocol			INTEGER,
				portTriggerIncomingPort		OCTET STRING,
				portTriggerIncomingProtocol	INTEGER,
        		portTriggerDelEntry			INTEGER
    		}                           
    
	portTriggerIndex	OBJECT-TYPE
				SYNTAX INTEGER	(1..32)
				MAX-ACCESS not-accessible
				STATUS current
				DESCRIPTION 
					"Port trigger index."
				::= { portTriggerEntry 1 }

	portTriggerDescription	OBJECT-TYPE
				SYNTAX OCTET STRING ( SIZE (1..18) )
				MAX-ACCESS read-write
				STATUS current
				DESCRIPTION
					"Description of port trigger list."
				::= { portTriggerEntry 2 }

	portTriggerPort		OBJECT-TYPE
				SYNTAX OCTET STRING ( SIZE (1..11) )
				MAX-ACCESS read-write
				STATUS current
				DESCRIPTION
					"Port of port trigger list."
				::= { portTriggerEntry 3 }

	portTriggerProtocol	OBJECT-TYPE
				SYNTAX INTEGER { tcp(1), udp(2) }
				MAX-ACCESS read-write
				STATUS current
				DESCRIPTION
					"Protocol of port trigger list."
				::= { portTriggerEntry 4 }

	portTriggerIncomingPort		OBJECT-TYPE
				SYNTAX OCTET STRING ( SIZE (1..11) )
				MAX-ACCESS read-write
				STATUS current
				DESCRIPTION
					"Incoming port of port trigger list."
				::= { portTriggerEntry 5 }

	portTriggerIncomingProtocol	OBJECT-TYPE
				SYNTAX INTEGER { tcp(1), udp(2) }
				MAX-ACCESS read-write
				STATUS current
				DESCRIPTION
					"Incoming protocol of port trigger list."
				::= { portTriggerEntry 6 }

	portTriggerDelEntry	OBJECT-TYPE
				SYNTAX INTEGER { yes(1), no(2) }
				MAX-ACCESS read-write
				STATUS current
				DESCRIPTION
					"Delete the port trigger enntry."
				::= { portTriggerEntry 7 }

-- **********************************************************************
-- *  End of Port Trigger Config Section 
-- **********************************************************************

-- **********************************************************************
-- *  Virtual server / Port Forwarding Config Section 
-- **********************************************************************

	port-forwarding		OBJECT IDENTIFIER ::= { wan 4 }

	enablePortForwarding	OBJECT-TYPE
				SYNTAX INTEGER { yes(1), no(2) }
				MAX-ACCESS read-write
				STATUS current
				DESCRIPTION ""
				::= { port-forwarding 1 }

	ftpServerPort		OBJECT-TYPE
				SYNTAX INTEGER ( 1..65535 )
				MAX-ACCESS read-write
				STATUS current
				DESCRIPTION ""
				::= { port-forwarding 2 }

	wClientListAct		OBJECT-TYPE
				SYNTAX INTEGER { scan(1), nothing(2) }
				MAX-ACCESS read-write
				STATUS current
				DESCRIPTION ""
				::= { port-forwarding 3 }

	wClientTable		OBJECT-TYPE
				SYNTAX SEQUENCE OF WClientEntry
				MAX-ACCESS not-accessible
				STATUS current
				DESCRIPTION ""
                                ::= { port-forwarding 4 }

	wClientEntry		OBJECT-TYPE
				SYNTAX WClientEntry
				MAX-ACCESS not-accessible
				STATUS current
				DESCRIPTION ""
				INDEX { wClientIndex }
				::= { wClientTable 1 }

 	WClientEntry ::= SEQUENCE {
        	wClientIndex    	INTEGER,
        	wClientIPAddr	        IpAddress,
        	wClientName		OCTET STRING
    	}

	wClientIndex		OBJECT-TYPE
				SYNTAX INTEGER ( 1..32 )
				MAX-ACCESS not-accessible
				STATUS current
				DESCRIPTION
					"Client entry index."
				::= { wClientEntry 1 }

	wClientIPAddr		OBJECT-TYPE
				SYNTAX IpAddress
				MAX-ACCESS read-only
				STATUS current
				DESCRIPTION
					"MAC address of the client list."
				::= { wClientEntry 2 }

	wClientName		OBJECT-TYPE
				SYNTAX OCTET STRING
				MAX-ACCESS read-only
				STATUS current
				DESCRIPTION
					"Name of the client list."
				::= { wClientEntry 3 }

	portForwardingTable	OBJECT-TYPE
				SYNTAX SEQUENCE OF PortForwardingEntry
				MAX-ACCESS not-accessible
				STATUS current
				DESCRIPTION
					"Port forwarding list."
				::= { port-forwarding 5 }

	portForwardingEntry	OBJECT-TYPE
				SYNTAX PortForwardingEntry
				MAX-ACCESS not-accessible
				STATUS current
				DESCRIPTION ""
				INDEX { portForwardingIndex }
				::= { portForwardingTable 1 }

 	PortForwardingEntry ::= SEQUENCE {
        	portForwardingIndex		INTEGER,
		portForwardingServiceName	OCTET STRING,
		portForwardingPortRange		OCTET STRING,
		portForwardingLocalIP		IpAddress,
		portForwardingLocalPort		INTEGER,
		portForwardingProtocol		INTEGER,
        	portForwardingDelEntry		INTEGER
    	}                           
    
	portForwardingIndex	OBJECT-TYPE
				SYNTAX INTEGER (1..32)
				MAX-ACCESS not-accessible
				STATUS current
				DESCRIPTION 
					"Port Forwarding Index."
				::= { portForwardingEntry 1 }

	portForwardingServiceName	OBJECT-TYPE
				SYNTAX OCTET STRING ( SIZE (1..30) )
				MAX-ACCESS read-write
				STATUS current
				DESCRIPTION
					"Service name of port forwarding list."
				::= { portForwardingEntry 2 }

	portForwardingPortRange		OBJECT-TYPE
				SYNTAX OCTET STRING
				MAX-ACCESS read-write
				STATUS current
				DESCRIPTION
					"Port range of port forwarding list."
				::= { portForwardingEntry 3 }

	portForwardingLocalIP		OBJECT-TYPE
				SYNTAX IpAddress
				MAX-ACCESS read-write
				STATUS current
				DESCRIPTION
					"Local IP of port forwarding list."
				::= { portForwardingEntry 4 }

	portForwardingLocalPort	OBJECT-TYPE
				SYNTAX INTEGER (1..65535)
				MAX-ACCESS read-write
				STATUS current
				DESCRIPTION
					"Local port of port forwarding list."
				::= { portForwardingEntry 5 }

	portForwardingProtocol	OBJECT-TYPE
				SYNTAX INTEGER { tcp(1), udp(2), both(3), other(4) }
				MAX-ACCESS read-write
				STATUS current
				DESCRIPTION
					"Protocol of port forwarding list."
				::= { portForwardingEntry 6 }

	portForwardingDelEntry	OBJECT-TYPE
				SYNTAX INTEGER { yes(1), no(2) }
				MAX-ACCESS read-write
				STATUS current
				DESCRIPTION
					"Delete the port forwarding entry."
				::= { portForwardingEntry 7 }

-- **********************************************************************
-- *  End of Virtual server / Port Forwarding Config Section 
-- **********************************************************************

-- **********************************************************************
-- *   DMZ Config Section 
-- **********************************************************************

	dmz			OBJECT IDENTIFIER ::= { wan 5 }

	enableDMZ	OBJECT-TYPE
				SYNTAX INTEGER { yes(1), no(2) }
				MAX-ACCESS read-write
				STATUS current
				DESCRIPTION ""
				::= { dmz 1 }

	exposedStationIPAddr	OBJECT-TYPE
				SYNTAX OCTET STRING ( SIZE (0..15) )
				MAX-ACCESS read-write
				STATUS current
				DESCRIPTION "If IP Address of Exposed Station is not set(blank), DMZ is disabled."
				::= { dmz 2 }

-- **********************************************************************
-- *  End of DMZ Config Section 
-- **********************************************************************

-- **********************************************************************
-- *   DDNS Config Section 
-- **********************************************************************

	ddns		OBJECT IDENTIFIER ::= { wan 6 }

	enableDDNSClient	OBJECT-TYPE
				SYNTAX INTEGER { yes(1), no(2) }
				MAX-ACCESS read-write
				STATUS current
				DESCRIPTION ""
				::= { ddns 1 }

	ddnsServer	OBJECT-TYPE
				SYNTAX INTEGER { asus(1), dyndns(2), dyndns-custom(3), dyndns-static(4), tzo(5), zoneedit(6), dnsomatic(7), tunnelbroker(8), no-ip(9) }
				MAX-ACCESS read-write
				STATUS current
				DESCRIPTION ""
				::= { ddns 2 }

	ddnsHostName	OBJECT-TYPE
                SYNTAX OCTET STRING ( SIZE (1..63) )
                MAX-ACCESS read-write
                STATUS current
                DESCRIPTION
					"The host name cannot accept number prefix and '.' (such as '123abc' or 'aaa.bbb')."
               	::= { ddns 3 }

	ddnsUserNameOrMail	OBJECT-TYPE
                SYNTAX OCTET STRING ( SIZE (1..32) )
                MAX-ACCESS read-write
                STATUS current
                DESCRIPTION ""
                ::= { ddns 4 }

	ddnsPasswordOrKey	OBJECT-TYPE
                SYNTAX OCTET STRING ( SIZE (1..64) )
                MAX-ACCESS read-write
                STATUS current
                DESCRIPTION ""
                ::= { ddns 5 }

	enableWildcard	OBJECT-TYPE
				SYNTAX INTEGER { yes(1), no(2) }
				MAX-ACCESS read-write
				STATUS current
				DESCRIPTION ""
				::= { ddns 6 }

-- **********************************************************************
-- *  End of DDNS Config Section 
-- **********************************************************************

-- **********************************************************************
-- *   NAT Passthrough Config Section 
-- **********************************************************************

	nat-passthrough		OBJECT IDENTIFIER ::= { wan 7 }

	pptpPassthrough		OBJECT-TYPE
				SYNTAX INTEGER { enable(1), disable(2) }
				MAX-ACCESS read-write
				STATUS current
				DESCRIPTION ""
				::= { nat-passthrough 1 }

	l2tpPassthrough		OBJECT-TYPE
				SYNTAX INTEGER { enable(1), disable(2) }
				MAX-ACCESS read-write
				STATUS current
				DESCRIPTION ""
				::= { nat-passthrough 2 }

	ipsecPassthrough		OBJECT-TYPE
				SYNTAX INTEGER { enable(1), disable(2) }
				MAX-ACCESS read-write
				STATUS current
				DESCRIPTION ""
				::= { nat-passthrough 3 }

	rtspPassthrough		OBJECT-TYPE
				SYNTAX INTEGER { enable(1), disable(2) }
				MAX-ACCESS read-write
				STATUS current
				DESCRIPTION ""
				::= { nat-passthrough 4 }

	h323Passthrough		OBJECT-TYPE
				SYNTAX INTEGER { enable(1), disable(2) }
				MAX-ACCESS read-write
				STATUS current
				DESCRIPTION ""
				::= { nat-passthrough 5 }

	sipPassthrough		OBJECT-TYPE
				SYNTAX INTEGER { enable(1), disable(2) }
				MAX-ACCESS read-write
				STATUS current
				DESCRIPTION ""
				::= { nat-passthrough 6 }

	pppoeRelay		OBJECT-TYPE
				SYNTAX INTEGER { enable(1), disable(2) }
				MAX-ACCESS read-write
				STATUS current
				DESCRIPTION
					"Enable PPPoE relay allows devices in LAN to establish a individual PPPoE connections that 
					passes through NAT."
				::= { nat-passthrough 7 }

-- **********************************************************************
-- *  End of NAT Passthrough Config Section 
-- **********************************************************************

-- ======================================================================
-- * End of WAN Section
-- ======================================================================





-- ======================================================================
-- * IPv6 Section
-- ======================================================================

-- **********************************************************************
-- *  IPv6 Config Section 
-- **********************************************************************
	basic-config-ipv6	OBJECT IDENTIFIER ::= { ipv6 1 }

	connectionType	OBJECT-TYPE
				SYNTAX INTEGER { disable(1), native(2), tunnel-6to4(3), tunnel-6in4(4), tunnel-6rd(5), static-ipv6(6) }
				MAX-ACCESS read-write
				STATUS current
				DESCRIPTION ""
				::= { basic-config-ipv6 1 }

	nativeDhcpPd	OBJECT-TYPE
				SYNTAX INTEGER { disable(0), enable(1) }
				MAX-ACCESS read-write
				STATUS current
				DESCRIPTION ""
				::= { basic-config-ipv6 2 }

	serverIPv4Address	OBJECT-TYPE
				SYNTAX IpAddress
				MAX-ACCESS read-write
				STATUS current
				DESCRIPTION ""
				::= { basic-config-ipv6 3 }

	ipv4AnycastRelay	OBJECT-TYPE
				SYNTAX IpAddress
				MAX-ACCESS read-write
				STATUS current
				DESCRIPTION ""
				::= { basic-config-ipv6 4 }

	dhcpOption		OBJECT-TYPE
				SYNTAX INTEGER { enable(1), disable(2) }
				MAX-ACCESS read-write
				STATUS current
				DESCRIPTION ""
				::= { basic-config-ipv6 5 }

	ipv6Prefix		OBJECT-TYPE
				SYNTAX OCTET STRING ( SIZE (1..39) )
				MAX-ACCESS read-write
				STATUS current
				DESCRIPTION ""
                ::= { basic-config-ipv6 6 }

	ipv6PrefixLength6rd	OBJECT-TYPE
				SYNTAX INTEGER ( 3..64 )
				MAX-ACCESS read-write
				STATUS current
				DESCRIPTION ""
				::= { basic-config-ipv6 7 }

	ipv4BorderRouter	OBJECT-TYPE
				SYNTAX IpAddress
				MAX-ACCESS read-write
				STATUS current
				DESCRIPTION ""
				::= { basic-config-ipv6 8 }

	ipv4RouterMaskLength	OBJECT-TYPE
				SYNTAX INTEGER ( 0..32 )
				MAX-ACCESS read-write
				STATUS current
				DESCRIPTION ""
				::= { basic-config-ipv6 9 }

	clientIPv6Address	OBJECT-TYPE
				SYNTAX OCTET STRING ( SIZE (1..39) )
				MAX-ACCESS read-write
				STATUS current
				DESCRIPTION ""
                ::= { basic-config-ipv6 10 }

	ipv6PrefixLength6in4	OBJECT-TYPE
				SYNTAX INTEGER	( 3..64 )
				MAX-ACCESS read-write
				STATUS current
				DESCRIPTION ""
				::= { basic-config-ipv6 11 }

	tunnelMTU	OBJECT-TYPE
				SYNTAX INTEGER ( 1280..1480 )
				MAX-ACCESS read-write
				STATUS current
				DESCRIPTION ""
				::= { basic-config-ipv6 12 }

	tunnelTTL	OBJECT-TYPE
				SYNTAX INTEGER ( 0..255 )
				MAX-ACCESS read-write
				STATUS current
				DESCRIPTION ""
				::= { basic-config-ipv6 13 }	

	wan-setting-ipv6	OBJECT IDENTIFIER ::= { ipv6 2 }

	wanIPv6Address		OBJECT-TYPE
				SYNTAX OCTET STRING ( SIZE (1..39) )
				MAX-ACCESS read-write
				STATUS current
				DESCRIPTION ""
                ::= { wan-setting-ipv6 1 }

	wanPrefixLength		OBJECT-TYPE
				SYNTAX INTEGER ( 3..64 )
				MAX-ACCESS read-write
				STATUS current
				DESCRIPTION ""
				::= { wan-setting-ipv6 2 }

	wanIPv6Gateway		OBJECT-TYPE
				SYNTAX OCTET STRING ( SIZE (1..39) )
				MAX-ACCESS read-write
				STATUS current
				DESCRIPTION ""
                ::= { wan-setting-ipv6 3 }

	lan-setting-ipv6	OBJECT IDENTIFIER ::= { ipv6 3 }    
	
	lanIpv6Address	OBJECT-TYPE
				SYNTAX OCTET STRING ( SIZE (1..39) )
				MAX-ACCESS read-write
				STATUS current
				DESCRIPTION ""
                ::= { lan-setting-ipv6 1 }	
                                              
	lanIpv6PrefixLength	OBJECT-TYPE
				SYNTAX INTEGER ( 3..64 )
				MAX-ACCESS read-write
				STATUS current
				DESCRIPTION ""
				::= { lan-setting-ipv6 2 }
                                              
	lanIpv6Prefix	OBJECT-TYPE
				SYNTAX OCTET STRING ( SIZE (1..39) )
				MAX-ACCESS read-write
				STATUS current
				DESCRIPTION ""
                ::= { lan-setting-ipv6 3 }      

   	lanIpv6AutoConfiguration	OBJECT-TYPE
				SYNTAX INTEGER { stateless(1), stateful(2) }
				MAX-ACCESS read-write
				STATUS current
				DESCRIPTION ""
				::= { lan-setting-ipv6 4 }
                                                    
 	lanIpv6LifeTime	OBJECT-TYPE
				SYNTAX INTEGER ( 120..60480 )
				MAX-ACCESS read-write
				STATUS current
				DESCRIPTION ""
				::= { lan-setting-ipv6 5 }
                                                    
 	lanIpv6DhcpPoolStartPrefix	OBJECT-TYPE
				SYNTAX OCTET STRING
				MAX-ACCESS read-only
				STATUS current
				DESCRIPTION ""
				::= { lan-setting-ipv6 6 }    
				                                                    
 	lanIpv6DhcpPoolStart	OBJECT-TYPE
				SYNTAX OCTET STRING ( SIZE (1..4) )
				MAX-ACCESS read-write
				STATUS current
				DESCRIPTION 
					" Value Range: 0001-ffff "
				::= { lan-setting-ipv6 7 }      

 	lanIpv6DhcpPoolEndPrefix	OBJECT-TYPE
				SYNTAX OCTET STRING
				MAX-ACCESS read-only
				STATUS current
				DESCRIPTION ""
				::= { lan-setting-ipv6 8 }    
								
 	lanIpv6DhcpPoolEnd	OBJECT-TYPE
				SYNTAX OCTET STRING ( SIZE (1..4) )
				MAX-ACCESS read-write
				STATUS current
				DESCRIPTION 
					" Value Range: 0001-ffff "
				::= { lan-setting-ipv6 9 }                                                    

	dns-setting-ipv6	OBJECT IDENTIFIER ::= { ipv6 4 }

	ipv6ConnectToDNSServerAuto	OBJECT-TYPE
				SYNTAX INTEGER { enable(1), disable(2) }
				MAX-ACCESS read-write
				STATUS current
				DESCRIPTION
					"Allows this router to get the DNS IP address from the ISP automatically."
				::= { dns-setting-ipv6 1 }

	ipv6DNSServer1	OBJECT-TYPE
				SYNTAX OCTET STRING ( SIZE(0..39) )
				MAX-ACCESS read-write
				STATUS current
				DESCRIPTION ""
                ::= { dns-setting-ipv6 2 }
                
	ipv6DNSServer2	OBJECT-TYPE
				SYNTAX OCTET STRING ( SIZE(0..39) )
				MAX-ACCESS read-write
				STATUS current
				DESCRIPTION ""
                ::= { dns-setting-ipv6 3 }

	ipv6DNSServer3	OBJECT-TYPE	
				SYNTAX OCTET STRING ( SIZE (0..39) )
				MAX-ACCESS read-write
				STATUS current
				DESCRIPTION ""
                ::= { dns-setting-ipv6 4 }	

	auto-configuration-setting	OBJECT IDENTIFIER ::= { ipv6 5 }

	enableRouterAdvertisement		OBJECT-TYPE
				SYNTAX INTEGER { enable(1), disable(2) }
				MAX-ACCESS read-write
				STATUS current
				DESCRIPTION ""
				::= { auto-configuration-setting 1 }

-- **********************************************************************
-- *  End of IPv6 Config Section 
-- **********************************************************************





-- ======================================================================
-- * VPN Server Section
-- ======================================================================

-- **********************************************************************
-- *  VPN Server Section 
-- **********************************************************************

	vpn-server-setting	OBJECT IDENTIFIER ::= { vpn 1 }     
	
	general-setting	    OBJECT IDENTIFIER ::= { vpn-server-setting 1 } 

	basic-config-vpn	OBJECT IDENTIFIER ::= { general-setting 1 }

	enableVPNServer	OBJECT-TYPE
				SYNTAX INTEGER { off(0), on(1) }
				MAX-ACCESS read-write
				STATUS current
				DESCRIPTION ""
				::= { basic-config-vpn 1 }

	vpnServerMode	OBJECT-TYPE
				SYNTAX INTEGER { pptp(1), openVPN(2) }
				MAX-ACCESS read-write
				STATUS current
				DESCRIPTION ""
				::= { basic-config-vpn 2 }

	sambaSupport	OBJECT-TYPE
				SYNTAX INTEGER { yes(1), no(2) }
				MAX-ACCESS read-write
				STATUS current
				DESCRIPTION ""
				::= { basic-config-vpn 3 }
                                                    
	exportOVPNCfgFile 	OBJECT IDENTIFIER ::= { basic-config-vpn 4 } 
	
	oVPNCfgFileTftpSrv	OBJECT-TYPE
				SYNTAX OCTET STRING ( SIZE (0..39) )
				MAX-ACCESS read-write
				STATUS current
				DESCRIPTION
					"Tftp server ip."
                ::= { exportOVPNCfgFile 1 }

	oVPNCfgFileExport	OBJECT-TYPE
				SYNTAX INTEGER { export(1), nothing(2) }
				MAX-ACCESS read-write
				STATUS current
				DESCRIPTION
					"Export OpenVPN configuration file."
				::= { exportOVPNCfgFile 2 }   
       
	username-and-password	OBJECT IDENTIFIER ::= { general-setting 2 }

	vpnUserTable	OBJECT-TYPE
				SYNTAX SEQUENCE OF VpnUserEntry
				MAX-ACCESS not-accessible
				STATUS current
				DESCRIPTION
					"VPN user list."
				::= { username-and-password 1 }

	vpnUserEntry	OBJECT-TYPE
				SYNTAX VpnUserEntry
				MAX-ACCESS not-accessible
				STATUS current
				DESCRIPTION ""
				INDEX { vpnUserIndex }
				::= { vpnUserTable 1 }

 	VpnUserEntry ::= SEQUENCE {
        	vpnUserIndex		INTEGER,
			vpnUserUserName		OCTET STRING,
			vpnUserPassword		OCTET STRING,
			vpnConnectionStatus INTEGER,    
			vpnIp				OCTET STRING,
  			vpnRemoteIp	        OCTET STRING,
        	vpnUserDelEntry		INTEGER
    	}                           
    
	vpnUserIndex	OBJECT-TYPE
				SYNTAX INTEGER   ( 1..16 )
				MAX-ACCESS not-accessible
				STATUS current
				DESCRIPTION 
					"VPN user index."
				::= { vpnUserEntry 1 }

	vpnUserUserName	OBJECT-TYPE
				SYNTAX OCTET STRING ( SIZE (1..32) )
				MAX-ACCESS read-write
				STATUS current
				DESCRIPTION
					"User name of vpn user list."
				::= { vpnUserEntry 2 }

	vpnUserPassword		OBJECT-TYPE
				SYNTAX OCTET STRING ( SIZE (1..16) )
				MAX-ACCESS read-write
				STATUS current
				DESCRIPTION
					"Password of vpn user list."
				::= { vpnUserEntry 3 }
				
	vpnConnectionStatus	OBJECT-TYPE
				SYNTAX INTEGER { connected(1), disconnected(2) }
				MAX-ACCESS read-only
				STATUS current
				DESCRIPTION
					"Connectin status of the user."
				::= { vpnUserEntry 4 }   
				 
	vpnIp		OBJECT-TYPE
				SYNTAX OCTET STRING				
				MAX-ACCESS read-only
				STATUS current
				DESCRIPTION
					"VPN Ip."
				::= { vpnUserEntry 5 }
		
	vpnRemoteIp	OBJECT-TYPE
				SYNTAX OCTET STRING
				MAX-ACCESS read-only
				STATUS current
				DESCRIPTION
					"Remote ip of vpn client."
				::= { vpnUserEntry 6 }

	vpnUserDelEntry	OBJECT-TYPE
				SYNTAX INTEGER { yes(1), no(2) }
				MAX-ACCESS read-write
				STATUS current
				DESCRIPTION
					"Delete the vpn user enntry."
				::= { vpnUserEntry 7 }

-- **********************************************************************
-- *  End of VPN Server Config Section 
-- **********************************************************************

-- **********************************************************************
-- *  VPN Server Advanced Settings Section 
-- **********************************************************************
	vpn-advnaced-settings	OBJECT IDENTIFIER ::= { vpn-server-setting 2 }

	vbroadcastSupport	OBJECT-TYPE
				SYNTAX INTEGER { disable(1), lan-to-vpn-client(2), vpn-client-to-lan(3), both(4) }
				MAX-ACCESS read-write
				STATUS current
				DESCRIPTION ""
				::= { vpn-advnaced-settings 1 }

	vAuthentication		OBJECT-TYPE
				SYNTAX INTEGER { auto(1), ms-chapv1(2), ms-chapv2(3) }
				MAX-ACCESS read-write
				STATUS current
				DESCRIPTION ""
				::= { vpn-advnaced-settings 2 }

	vmppeEncryption		OBJECT-TYPE
				SYNTAX BITS { mppe-128(0), mppe-40(1), no-encryption(2) }
				MAX-ACCESS read-write
				STATUS current
				DESCRIPTION ""
				::= { vpn-advnaced-settings 3 }

	vconnectToDNSServerAuto	OBJECT-TYPE
				SYNTAX INTEGER { yes(1), no(2) }
				MAX-ACCESS read-write
				STATUS current
				DESCRIPTION ""
				::= { vpn-advnaced-settings 4 }

	vDNSServer1		OBJECT-TYPE
				SYNTAX OCTET STRING ( SIZE (0..15) )
				MAX-ACCESS read-write
				STATUS current
				DESCRIPTION ""
				::= { vpn-advnaced-settings 5 }

	vDNSServer2		OBJECT-TYPE
				SYNTAX OCTET STRING ( SIZE (0..15) )
				MAX-ACCESS read-write
				STATUS current
				DESCRIPTION ""
				::= { vpn-advnaced-settings 6 }

	vconnectToWINSServerAuto	OBJECT-TYPE
				SYNTAX INTEGER { yes(1), no(2) }
				MAX-ACCESS read-write
				STATUS current
				DESCRIPTION ""
				::= { vpn-advnaced-settings 7 }

	vWINSServer1	OBJECT-TYPE
				SYNTAX OCTET STRING ( SIZE (0..15) )
				MAX-ACCESS read-write
				STATUS current
				DESCRIPTION ""
				::= { vpn-advnaced-settings 8 }

	vWINSServer2	OBJECT-TYPE
				SYNTAX OCTET STRING ( SIZE (0..15) )
				MAX-ACCESS read-write
				STATUS current
				DESCRIPTION ""
				::= { vpn-advnaced-settings 9 }
                           
	vMRU		OBJECT-TYPE
				SYNTAX INTEGER
				MAX-ACCESS read-write
				STATUS current
				DESCRIPTION ""
				::= { vpn-advnaced-settings 10 }
				                          
	vMTU		OBJECT-TYPE
				SYNTAX INTEGER
				MAX-ACCESS read-write
				STATUS current
				DESCRIPTION ""
				::= { vpn-advnaced-settings 11 }				                           
				                           
	vclientStartIPAddress	OBJECT-TYPE
				SYNTAX IpAddress
				MAX-ACCESS read-write
				STATUS current
				DESCRIPTION ""
				::= { vpn-advnaced-settings 12 }

	vclientEndIPAddress	OBJECT-TYPE
				SYNTAX INTEGER ( 1..255 )
				MAX-ACCESS read-write
				STATUS current
				DESCRIPTION "Maximum 10 clients"
				::= { vpn-advnaced-settings 13 }

-- **********************************************************************
-- *  End of VPN Server Advanced Settings Section 
-- **********************************************************************

-- ======================================================================
-- * VPN Client Section
-- ======================================================================
	vpn-client-setting	OBJECT IDENTIFIER ::= { vpn 2 }          
	
	vpnServerTable	OBJECT-TYPE
				SYNTAX SEQUENCE OF VpnServerEntry
				MAX-ACCESS not-accessible
				STATUS current
				DESCRIPTION
					"VPN server list."
				::= { vpn-client-setting 1 }

	vpnServerEntry	OBJECT-TYPE
				SYNTAX VpnServerEntry
				MAX-ACCESS not-accessible
				STATUS current
				DESCRIPTION ""
				INDEX { vpnServerIndex }
				::= { vpnServerTable 1 }

 	VpnServerEntry ::= SEQUENCE {
        	vpnServerIndex				INTEGER,
			vpnServerDesc				OCTET STRING,
			vpnServerType				INTEGER,    
			vpnServerIP					OCTET STRING,  
			vpnServerUsername			OCTET STRING,
			vpnServerPwd				OCTET STRING,
			vpnServerConnectionStatus 	INTEGER,
        	vpnServerDelEntry			INTEGER,
        	vpnServerConnect			INTEGER
    	}                           

	vpnServerIndex	OBJECT-TYPE
				SYNTAX INTEGER   ( 1..10 )
				MAX-ACCESS not-accessible
				STATUS current
				DESCRIPTION 
					"VPN server index."
				::= { vpnServerEntry 1 }    
	
	vpnServerDesc	OBJECT-TYPE
				SYNTAX OCTET STRING ( SIZE (1..32) )
				MAX-ACCESS read-write
				STATUS current
				DESCRIPTION
					"Description of vpn server."
				::= { vpnServerEntry 2 }

	vpnServerType	OBJECT-TYPE
				SYNTAX INTEGER { pptp(1), l2tp(2), openVPN(3), none(0) }
				MAX-ACCESS read-write
				STATUS current
				DESCRIPTION 
					"There can be only one OpenVPN profile."
				::= { vpnServerEntry 3 }     
				
	vpnServerIP		OBJECT-TYPE
				SYNTAX OCTET STRING
				MAX-ACCESS read-write
				STATUS current
				DESCRIPTION ""
				::= { vpnServerEntry 4 }
				

	vpnServerUsername	OBJECT-TYPE
				SYNTAX OCTET STRING ( SIZE (1..32) )
				MAX-ACCESS read-write
				STATUS current
				DESCRIPTION
					"User name of VPN server."
				::= { vpnServerEntry 5 }

	vpnServerPwd	OBJECT-TYPE
				SYNTAX OCTET STRING ( SIZE (1..16) )
				MAX-ACCESS read-write
				STATUS current
				DESCRIPTION
					"Password of VPN server."
				::= { vpnServerEntry 6 }
				
	vpnServerConnectionStatus	OBJECT-TYPE
				SYNTAX INTEGER { connected(1), disconnected(2) }
				MAX-ACCESS read-only
				STATUS current
				DESCRIPTION
					"Connectin status of VPN server."
				::= { vpnServerEntry 7 }
      
	
	vpnServerDelEntry	OBJECT-TYPE
				SYNTAX INTEGER { yes(1), no(2) }
				MAX-ACCESS read-write
				STATUS current
				DESCRIPTION
					"Delete the VPN server entry."
				::= { vpnServerEntry 8 }   
				
	vpnServerConnect	OBJECT-TYPE
				SYNTAX INTEGER { connect(1), disconnect(2), nothing(3) }
				MAX-ACCESS read-write
				STATUS current
				DESCRIPTION
					"Connect to the VPN server."
				::= { vpnServerEntry 9 }  				    
				
	openVPNFile 	OBJECT IDENTIFIER ::= { vpn-client-setting 2 }     
	
	openVPNImportFile 	OBJECT IDENTIFIER ::= { openVPNFile 1 } 
	
	openVPNTftpSrv		OBJECT-TYPE
				SYNTAX OCTET STRING ( SIZE (0..39) )
				MAX-ACCESS read-write
				STATUS current
				DESCRIPTION
					"Tftp server ip."
                ::= { openVPNImportFile 1 }

	openVPNFileType		OBJECT-TYPE
				SYNTAX INTEGER { ovpn(1), ca(2), cert(3), key(4), static(5), none(0) }
				MAX-ACCESS read-write
				STATUS current
				DESCRIPTION
					"Type of imported file. 
						ovnp: .ovpn file   
						  ca: Certificate Authority  
						cert: Client Certificate 
						 key: Client Key
					  static: Static Key "
				::= { openVPNImportFile 2 } 
				  
	openVPNFileName		OBJECT-TYPE
				SYNTAX OCTET STRING
				MAX-ACCESS read-write
				STATUS current
				DESCRIPTION
					"The file name of the .vpn file or CA file which will be imported to the device."
				::= { openVPNImportFile 3 }

	openVPNFileImport	OBJECT-TYPE
				SYNTAX INTEGER { import(1), nothing(2) }
				MAX-ACCESS read-write
				STATUS current
				DESCRIPTION
					"Import will upload the .vpn file or CA file to the device."
				::= { openVPNImportFile 4 }   
				
	openVPNManualSetting	OBJECT IDENTIFIER ::= { openVPNFile 2 }
				
	openVPNCertAuth		OBJECT-TYPE
                SYNTAX OCTET STRING
                MAX-ACCESS read-write
                STATUS current
				DESCRIPTION	
					"Certificate Authority"
				::= { openVPNManualSetting 1 } 
				
   	openVPNClientCert	OBJECT-TYPE
                SYNTAX OCTET STRING
                MAX-ACCESS read-write
                STATUS current
				DESCRIPTION	
					"Client Certificate"
				::= { openVPNManualSetting 2 } 

   	openVPNClientKey	OBJECT-TYPE
                SYNTAX OCTET STRING
                MAX-ACCESS read-write
                STATUS current
				DESCRIPTION	
					"Client Key"
				::= { openVPNManualSetting 3 } 
				
   	openVPNStaticKey	OBJECT-TYPE
                SYNTAX OCTET STRING
                MAX-ACCESS read-write
                STATUS current
				DESCRIPTION	"Static Key(Optional)"
				::= { openVPNManualSetting 4 } 	
							 
-- **********************************************************************
-- *  End of VPN Clients Section 
-- **********************************************************************
 
-- ======================================================================
-- * End of VPN Section
-- ======================================================================





-- ======================================================================
-- * Firewall Section
-- ======================================================================

-- **********************************************************************
-- *  General Section 
-- **********************************************************************

	firewall-general	OBJECT IDENTIFIER ::= { firewall 1 }

	enableFirewall		OBJECT-TYPE
				SYNTAX INTEGER { yes(1), no(2) }
				MAX-ACCESS read-write
				STATUS current
				DESCRIPTION
					"Disabling the firewall will deactivate all the related functions."
				::= { firewall-general 1 }

	enableDoSProtection	OBJECT-TYPE
				SYNTAX INTEGER { yes(1), no(2) }
				MAX-ACCESS read-write
				STATUS current
				DESCRIPTION
					"A 'denial-of-service' attack is an explicit attempt to deny legitimate users from using 
					a service or computer resource. Enabling this feature can protect the router from DoS attack 
					but it would increase the router's workload."
				::= { firewall-general 2 }

	loggedPacketsType	OBJECT-TYPE
				SYNTAX INTEGER { none(1), dropped(2), accepted(3), both(4) }
				MAX-ACCESS read-write
				STATUS current
				DESCRIPTION
					"This field indicates the kind of packets logged between LAN and WAN."
				::= { firewall-general 3 }

	respondPingRequestfromWAN	OBJECT-TYPE
				SYNTAX INTEGER { yes(1), no(2) }
				MAX-ACCESS read-write
				STATUS current
				DESCRIPTION
					"This feature allows you to respond to ping request from WAN."
				::= { firewall-general 4 }

-- **********************************************************************
-- *  End of General Config Section 
-- **********************************************************************

-- **********************************************************************
-- *  URL Filter Section 
-- **********************************************************************

	url-filter		OBJECT IDENTIFIER ::= { firewall 2 }

	basic-config-url OBJECT IDENTIFIER ::= { url-filter 1 }

	enableURLFilter	OBJECT-TYPE
				SYNTAX INTEGER { disable(0), enable(1)}
				MAX-ACCESS read-write
				STATUS current
				DESCRIPTION
					"This field defines the dates that URL filter will be enabled."
				::= { basic-config-url 1 }

	url-filter-list	OBJECT IDENTIFIER ::= { url-filter 2 }

	urlFilterTable	OBJECT-TYPE
				SYNTAX SEQUENCE OF UrlFilterEntry
				MAX-ACCESS not-accessible
				STATUS current
				DESCRIPTION
					"URL filter list."
				::= { url-filter-list 1 }

	urlFilterEntry	OBJECT-TYPE
				SYNTAX UrlFilterEntry
				MAX-ACCESS not-accessible
				STATUS current
				DESCRIPTION ""
				INDEX { urlFilterIndex }
				::= { urlFilterTable 1 }

 	UrlFilterEntry ::= SEQUENCE {
        		urlFilterIndex		INTEGER,
				urlFilterUrl		OCTET STRING,
        		urlFilterDelEntry	INTEGER
    		}                           
    
	urlFilterIndex		OBJECT-TYPE
				SYNTAX INTEGER  (1..128)
				MAX-ACCESS not-accessible
				STATUS current
				DESCRIPTION 
					"URL Filter Index."
				::= { urlFilterEntry 1 }

	urlFilterUrl		OBJECT-TYPE
				SYNTAX OCTET STRING ( SIZE (1..32) )
				MAX-ACCESS read-write
				STATUS current
				DESCRIPTION
					"URL of url filter list."
				::= { urlFilterEntry 2 }

	urlFilterDelEntry	OBJECT-TYPE
				SYNTAX INTEGER { yes(1), no(2) }
				MAX-ACCESS read-write
				STATUS current
				DESCRIPTION
					"Delete the url filter enntry."
				::= { urlFilterEntry 3 }

-- **********************************************************************
-- *  End of URL Filter Config Section 
-- **********************************************************************

-- **********************************************************************
-- *  Keyword Filter Section 
-- **********************************************************************

	keyword-filter	OBJECT IDENTIFIER ::= { firewall 3 }

	basic-config-keyword	OBJECT IDENTIFIER ::= { keyword-filter 1 }

	enableKeywordFilter	OBJECT-TYPE
				SYNTAX INTEGER { disable(0), enable(1) }
				MAX-ACCESS read-write
				STATUS current
				DESCRIPTION ""
				::= { basic-config-keyword 1 }

	keyword-filter-list	OBJECT IDENTIFIER ::= { keyword-filter 2 }

	keywordFilterTable	OBJECT-TYPE
				SYNTAX SEQUENCE OF KeywordFilterEntry
				MAX-ACCESS not-accessible
				STATUS current
				DESCRIPTION
					"Keyword filter list."
				::= { keyword-filter-list 1 }

	keywordFilterEntry	OBJECT-TYPE
				SYNTAX KeywordFilterEntry
				MAX-ACCESS not-accessible
				STATUS current
				DESCRIPTION ""
				INDEX { keywordFilterIndex }
				::= { keywordFilterTable 1 }

 	KeywordFilterEntry ::= SEQUENCE {
        	keywordFilterIndex		INTEGER,
			keywordFilterKeyword	OCTET STRING,
        	keywordFilterDelEntry	INTEGER
    	}                           
    
	keywordFilterIndex	OBJECT-TYPE
				SYNTAX INTEGER (1..128)
				MAX-ACCESS not-accessible
				STATUS current
				DESCRIPTION 
					"Keyword Filter Index."
				::= { keywordFilterEntry 1 }

	keywordFilterKeyword	OBJECT-TYPE
				SYNTAX OCTET STRING ( SIZE (1..32) )
				MAX-ACCESS read-write
				STATUS current
				DESCRIPTION
					"Keyword of keyword filter list."
				::= { keywordFilterEntry 2 }

	keywordFilterDelEntry	OBJECT-TYPE
				SYNTAX INTEGER { yes(1), no(2) }
				MAX-ACCESS read-write
				STATUS current
				DESCRIPTION
					"Delete the keyword filter enntry."
				::= { keywordFilterEntry 3 }

-- **********************************************************************
-- *  End of Keyword Filter Config Section 
-- **********************************************************************

-- **********************************************************************
-- *  Network Services Filter Section 
-- **********************************************************************

	network-services-filter	OBJECT IDENTIFIER ::= { firewall 4 }

	enableNetworkServicesFilter	OBJECT-TYPE
				SYNTAX INTEGER { yes(1), no(2) }
				MAX-ACCESS read-write
				STATUS current
				DESCRIPTION
					"Select [Yes] to enable filter that specify IP or port for control incoming and outgoing packets."
				::= { network-services-filter 1 }

	filterTableType		OBJECT-TYPE
				SYNTAX INTEGER { white-list(1), black-list(2) }
				MAX-ACCESS read-write
				STATUS current
				DESCRIPTION
					"Select either White List or Black List to accept or reject those LAN to WAN packet exchanges 
					for clients specified in the filter table."
				::= { network-services-filter 2 }

	weekDaysEnableLANtoWANFilter	OBJECT-TYPE
				SYNTAX BITS { monday(0), tuesday(1), wednesday(2), thursday(3), friday(4) }
				MAX-ACCESS read-write
				STATUS current
				DESCRIPTION
					"This field defines the dates that LAN to WAN filter will be enabled."
				::= { network-services-filter 3 }

	weekDaysFilterStartTimeH	OBJECT-TYPE
				SYNTAX INTEGER ( 0..23 )              
                MAX-ACCESS read-write
				STATUS current
				DESCRIPTION
					"Hour of starting time of weekdays to enable Network Services Filter."
				::= { network-services-filter 4 }

	weekDaysFilterStartTimeM	OBJECT-TYPE
				SYNTAX INTEGER ( 0..59 )
				MAX-ACCESS read-write
				STATUS current
				DESCRIPTION
					"Minute of starting time of weekdays to enable Network Services Filter."
				::= { network-services-filter 5 }

	weekDaysFilterEndTimeH	OBJECT-TYPE
				SYNTAX INTEGER ( 0..23 )              
                MAX-ACCESS read-write
				STATUS current
				DESCRIPTION
					"Hour of ending time of weekdays to enable Network Services Filter."
				::= { network-services-filter 6 }

	weekDaysFilterEndTimeM	OBJECT-TYPE
				SYNTAX INTEGER ( 0..59 )
				MAX-ACCESS read-write
				STATUS current
				DESCRIPTION
					"Minute of ending time of weekdays to enable Network Services Filter."
				::= { network-services-filter 7 }

	weekendEnableLANtoWANFilter	OBJECT-TYPE
				SYNTAX BITS { saturday(0), sunday(1) }
				MAX-ACCESS read-write
				STATUS current
				DESCRIPTION
					"This field defines the dates that LAN to WAN filter will be enabled."
				::= { network-services-filter 8 }

	weekendFilterStartTimeH	OBJECT-TYPE
				SYNTAX INTEGER ( 0..23 )              
                MAX-ACCESS read-write
				STATUS current
				DESCRIPTION
					"Hour of starting time of weekend to enable Network Services Filter."
				::= { network-services-filter 9 }

	weekendFilterStartTimeM	OBJECT-TYPE
				SYNTAX INTEGER ( 0..59 )
				MAX-ACCESS read-write
				STATUS current
				DESCRIPTION
					"Minute of starting time of weekend to enable Network Services Filter."
				::= { network-services-filter 10 }

	weekendFilterEndTimeH	OBJECT-TYPE
				SYNTAX INTEGER ( 0..23 )              
                MAX-ACCESS read-write
				STATUS current
				DESCRIPTION
					"Hour of ending time of weekend to enable Network Services Filter."
				::= { network-services-filter 11 }

	weekendFilterEndTimeM	OBJECT-TYPE
				SYNTAX INTEGER ( 0..59 )
				MAX-ACCESS read-write
				STATUS current
				DESCRIPTION
					"Minute of ending time of weekend to enable Network Services Filter."
				::= { network-services-filter 12 }

	filteredICMPPacketTypes	OBJECT-TYPE
				SYNTAX OCTET STRING ( SIZE (1..32) )
				MAX-ACCESS read-write
				STATUS current
				DESCRIPTION
					"This field defines a list of LAN to WAN ICMP packets type that will be filtered. For example, 
					if you would like to filter Echo(type 8) and Echo Reply(type 0) ICMP packets, you need to enter 
					a string with numbers separated by blank, such as, [0 8]."
				::= { network-services-filter 13 }

	networkServicesFilterTable	OBJECT-TYPE
				SYNTAX SEQUENCE OF NetworkServicesFilterEntry
				MAX-ACCESS not-accessible
				STATUS current
				DESCRIPTION
					"Network services filter list."
				::= { network-services-filter 14 }
                 	
	networkServicesFilterEntry	OBJECT-TYPE
				SYNTAX NetworkServicesFilterEntry
				MAX-ACCESS not-accessible
				STATUS current
				DESCRIPTION ""
				INDEX { networkServicesFilterIndex }
				::= { networkServicesFilterTable 1 }

 	NetworkServicesFilterEntry ::= SEQUENCE {
        	networkServicesFilterIndex					INTEGER,
			networkServicesFilterSourceIP				IpAddress,
			networkServicesFilterSourcePortRange		OCTET STRING,
			networkServicesFilterDestinationIP			IpAddress,
			networkServicesFilterDestinationPortRange	OCTET STRING,
			networkServicesFilterProtocol				INTEGER,
        	networkServicesFilterDelEntry				INTEGER
    	}                           
    
	networkServicesFilterIndex	OBJECT-TYPE
				SYNTAX INTEGER  (1..32)
				MAX-ACCESS not-accessible
				STATUS current
				DESCRIPTION 
					"Network Services Filter Index."
				::= { networkServicesFilterEntry 1 }

	networkServicesFilterSourceIP	OBJECT-TYPE
				SYNTAX IpAddress
				MAX-ACCESS read-write
				STATUS current
				DESCRIPTION
					"For source or destination IP address, you can : 
					(a) enter a specific IP address, such as '192.168.122.1'; 
					(b) enter IP addresses within one subnet or within the same IP pool, such as '192.168.123.*', 
					    or '192.168.*.*'; or 
					(c) enter all IP addresses as '*.*.*.*'."
				::= { networkServicesFilterEntry 2 }

	networkServicesFilterSourcePortRange	OBJECT-TYPE
				SYNTAX OCTET STRING ( SIZE (1..11) )
				MAX-ACCESS read-write
				STATUS current
				DESCRIPTION
					"For source or destination port range, you can either : 
					 a) enter a specific port, such as '95'; or 
					 b) enter ports within a range, such as '103:315', '>100', or '<65535'."
				::= { networkServicesFilterEntry 3 }

	networkServicesFilterDestinationIP	OBJECT-TYPE
				SYNTAX IpAddress
				MAX-ACCESS read-write
				STATUS current
				DESCRIPTION
					"For source or destination IP address, you can : 
					(a) enter a specific IP address, such as '192.168.122.1'; 
					(b) enter IP addresses within one subnet or within the same IP pool, such as '192.168.123.*', 
					    or '192.168.*.*'; or 
					(c) enter all IP addresses as '*.*.*.*'."
				::= { networkServicesFilterEntry 4 }

	networkServicesFilterDestinationPortRange	OBJECT-TYPE
				SYNTAX OCTET STRING ( SIZE (1..11) )
				MAX-ACCESS read-write
				STATUS current
				DESCRIPTION
					"For source or destination port range, you can either : 
					 a) enter a specific port, such as '95'; or 
					 b) enter ports within a range, such as '103:315', '>100', or '<65535'."
				::= { networkServicesFilterEntry 5 }

	networkServicesFilterProtocol	OBJECT-TYPE
				SYNTAX INTEGER {  tcp(1), tcp-all(2), tcp-syn(3), tcp-ack(4), tcp-fin(5), tcp-rst(6), tcp-urg(7), tcp-psh(8), udp(9), none(0) }
				MAX-ACCESS read-write
				STATUS current
				DESCRIPTION
					"Protocol type."
				::= { networkServicesFilterEntry 6 }

	networkServicesFilterDelEntry	OBJECT-TYPE
				SYNTAX INTEGER { yes(1), no(2) }
				MAX-ACCESS read-write
				STATUS current
				DESCRIPTION
					"Delete the network services filter enntry."
				::= { networkServicesFilterEntry 7 }

-- **********************************************************************
-- *  End of Network Services Filter Config Section 
-- **********************************************************************

-- **********************************************************************
-- *  IPv6 Firewall Config Section 
-- **********************************************************************
	ipv6-firewall	OBJECT IDENTIFIER ::= { firewall 5 }   
	
	enableIpv6Firewall	OBJECT-TYPE
				SYNTAX INTEGER { yes(1), no(2) }
				MAX-ACCESS read-write
				STATUS current
				DESCRIPTION
					"Select [Yes] to enable IPv6 firewall."
				::= { ipv6-firewall 1 }

 	inboundFirewallRulesTable	OBJECT-TYPE
				SYNTAX SEQUENCE OF InboundFirewallRulesEntry
				MAX-ACCESS not-accessible
				STATUS current
				DESCRIPTION
					"Network services filter list."
				::= { ipv6-firewall 2 }

	inboundFirewallRulesEntry	OBJECT-TYPE
				SYNTAX InboundFirewallRulesEntry
				MAX-ACCESS not-accessible
				STATUS current
				DESCRIPTION ""
				INDEX { inboundFirewallRulesIndex }
				::= { inboundFirewallRulesTable 1 }

 	InboundFirewallRulesEntry ::= SEQUENCE {
        	inboundFirewallRulesIndex					INTEGER,  
        	inboundFirewallRulesServiceName				OCTET STRING,
			inboundFirewallRulesRemoteIP				OCTET STRING,
			inboundFirewallRulesLocalIP					OCTET STRING,
			inboundFirewallRulesPortRange				OCTET STRING,
			inboundFirewallRulesProtocol				INTEGER,
        	inboundFirewallRulesDelEntry				INTEGER
    	}                           
    
	inboundFirewallRulesIndex	OBJECT-TYPE
				SYNTAX INTEGER  (1..128)
				MAX-ACCESS not-accessible
				STATUS current
				DESCRIPTION 
					"Inbound firewall rules Index."
				::= { inboundFirewallRulesEntry 1 }
                                                       
	inboundFirewallRulesServiceName	OBJECT-TYPE
				SYNTAX OCTET STRING ( SIZE (1..32) )
				MAX-ACCESS read-write
				STATUS current
				DESCRIPTION	""
				::= { inboundFirewallRulesEntry 2 }
                                                       
	inboundFirewallRulesRemoteIP	OBJECT-TYPE
				SYNTAX OCTET STRING
				MAX-ACCESS read-write
				STATUS current
				DESCRIPTION ""
				::= { inboundFirewallRulesEntry 3 }

	inboundFirewallRulesLocalIP	OBJECT-TYPE
				SYNTAX OCTET STRING
				MAX-ACCESS read-write
				STATUS current
				DESCRIPTION
					"Key in the LAN client's IP address."
				::= { inboundFirewallRulesEntry 4 }

	inboundFirewallRulesPortRange	OBJECT-TYPE
				SYNTAX OCTET STRING ( SIZE (1..11) )
				MAX-ACCESS read-write
				STATUS current
				DESCRIPTION
					"Port range accepts various formats such as Port Range (300:350), 
					 individual ports (566,789) or Mix (1015:1024,3021)."
				::= { inboundFirewallRulesEntry 5 }

	inboundFirewallRulesProtocol	OBJECT-TYPE
				SYNTAX INTEGER { tcp(1), udp(2), both(3), other(4), none(0) }
				MAX-ACCESS read-write
				STATUS current
				DESCRIPTION
					"Protocol type."
				::= { inboundFirewallRulesEntry 6 }

	inboundFirewallRulesDelEntry	OBJECT-TYPE
				SYNTAX INTEGER { yes(1), no(2) }
				MAX-ACCESS read-write
				STATUS current
				DESCRIPTION
					"Delete the inbound firewall rule."
				::= { inboundFirewallRulesEntry 7 }
  
-- **********************************************************************
-- *  End of IPv6 Firewall Config Section 
-- **********************************************************************
   
-- ======================================================================
-- * End of Firewall Section
-- ======================================================================





-- ======================================================================
-- * Administration Section
-- ======================================================================

-- **********************************************************************
-- *  Operation Mode Section 
-- **********************************************************************

	operation-mode	OBJECT IDENTIFIER ::= { administration 1 }

	operationMode	OBJECT-TYPE
				SYNTAX INTEGER { wireless-router-mode(1), repeater-mode(2), access-point-mode(3), media-bridge(4) }
				MAX-ACCESS read-write
				STATUS current
				DESCRIPTION
					"RT-AC66U supports several operation modes to meet different requirements. 
					Please select the mode that match your situation.					
					* In wireless router/ IP sharing mode, RT-AC66U connects to the Internet via 
					PPPoE, DHCP, PPTP, L2TP, or Static IP and shares the wireless network to LAN
					clients or devices. In this mode, NAT, firewall, and DHCP server are enabled 
					by default. UPnP and Dynamic DNS are supported for SOHO and home users. 
					Select this mode if you are a first-time user or 
					you are not currently using any wired/wireless routers.      
					* In Repeater mode, RT-AC66U wirelessly connects to an existing wireless network 
					to extend the wireless coverage. In this mode, the firewall, IP sharing, and 
					NAT functions are disabled.
					* In Access Point (AP) mode, RT-AC66U connects to a wireless router through an 
					Ethernet cable to extend the wireless signal coverage to other network clients. 
					In this mode, the firewall, IP sharing, and NAT functions are disabled by default.
					* RT-AC66U can be configured in Media bridge mode.The Media Bridge mode provides 
					the fastest 802.11ac Wi-Fi connection for multiple media devices simultaneously.
					To set up the Media Bridge mode, you need two RT-AC66U: one configured as the 
					Media station and the other as a router.Configure one RT-AC66U as a router 
					and another RT-AC66U as an 802.11ac Media bridge to provide a simultaneous 802.11ac
					Wi-Fi connection for your media devices such as computer, Smart TV, game console, 
					DVR, or media player via Ethernet cable.Change to Media Bridge mode to provide 
					a simultaneous 802.11ac Wi-Fi connection for your media devices. In media bridge 
					mode, only wireless devices connect to the P-AP. Client devices need to be connected
					to the media bridge with a network cable."
				::= { operation-mode 1 }

-- **********************************************************************
-- *  End of Operation Mode Config Section 
-- **********************************************************************

-- **********************************************************************
-- *  System Section 
-- **********************************************************************

	system		OBJECT IDENTIFIER ::= { administration 2 }

	login-password		OBJECT IDENTIFIER ::= { system 1 }

	routerLoginName		OBJECT-TYPE
				SYNTAX OCTET STRING ( SIZE (1..20) )
				MAX-ACCESS read-write
				STATUS current
				DESCRIPTION ""
				::= { login-password 1 }

	newPassword	OBJECT-TYPE
				SYNTAX OCTET STRING ( SIZE (1..16) )
				MAX-ACCESS read-write
				STATUS current
				DESCRIPTION
					"Password cannot be greater than 16 characters."
				::= { login-password 2 }

	miscellaneous	OBJECT IDENTIFIER ::= { system 2 }

	wpsButtonBehavior	OBJECT-TYPE
				SYNTAX INTEGER { toggle-radio(1), activate-wps(2) }
				MAX-ACCESS read-write
				STATUS current
				DESCRIPTION ""
				::= { miscellaneous 1 }

	remoteLogServer		OBJECT-TYPE
				SYNTAX IpAddress
				MAX-ACCESS read-write
				STATUS current
				DESCRIPTION
					"This field allows to assign a remote server to record log messages of RT-AC66U. If you 
					leave it blank, the system will record up to 1024 messages on RT-AC66U."
				::= { miscellaneous 2 }

	timeZone	OBJECT-TYPE
				SYNTAX INTEGER (1..86)
				MAX-ACCESS read-write
				STATUS current
				DESCRIPTION
					"
					1	(GMT-12:00) Eniwetok, Kwajalein
					2	(GMT-11:00) Midway Island, Samoa
					3	(GMT-10:00) Hawaii
					4	(GMT-09:00) Alaska
					5	(GMT-08:00) Pacific Time (US, Canada)
					6	(GMT-07:00) Mountain Time (US, Canada)
					7	(GMT-07:00) Arizona
					8	(GMT-07:00) Chihuahua, La Paz, Mazatlan
					9	(GMT-06:00) Central Time (US, Canada)
					10	(GMT-06:00) Saskatchewan
					11	(GMT-06:00) Guadalajara, Mexico City
					12	(GMT-06:00) Monterrey
					13	(GMT-06:00) Central America
					14	(GMT-05:00) Eastern Time (US, Canada)
					15	(GMT-05:00) Indiana (East)
					16	(GMT-05:00) Bogota, Lima, Quito
					17	(GMT-04:00) Atlantic Time (Canada)
					18	(GMT-04:00) Caracas, La Paz
					19	(GMT-04:00) Santiago
					20	(GMT-03:30) Newfoundland
					21	(GMT-03:00) Brasilia
					22	(GMT-03:00) Buenos Aires, Georgetown
					23	(GMT-03:00) Greenland
					24	(GMT-02:00) Mid-Atlantic
					25	(GMT-01:00) Azores
					26	(GMT-01:00) Cape Verde Is.
					27	(GMT) Greenwich Mean Time  
					28  (GMT) Dublin, Edinburgh, Lisbon, London
					29	(GMT) Casablanca, Monrovia
					30	(GMT+01:00) Belgrade, Bratislava, Budapest
					31	(GMT+01:00) Ljubljana, Prague
					32	(GMT+01:00) Sarajevo, Skopje, Sofija
					33	(GMT+01:00) Vilnius, Warsaw, Zagreb
					34	(GMT+01:00) Brussels, Copenhagen
					35	(GMT+01:00) Madrid, Paris
					36	(GMT+01:00) Amsterdam, Berlin, Bern
					37	(GMT+01:00) Rome, Stockholm, Vienna
					38	(GMT+01:00) West Central Africa
					39	(GMT+02:00) Bucharest
					40	(GMT+02:00) Cairo
	 				41	(GMT+02:00) Helsinki, Riga, Tallinn
					42	(GMT+02:00) Athens, Istanbul, Minsk
	 				43	(GMT+02:00) Jerusalem
	 				44	(GMT+02:00) Harare, Pretoria
					45	(GMT+02:00) Ukraine
					46	(GMT+03:00) Kaliningrad, Kuwait, Riyadh
					47	(GMT+03:00) Nairobi
					48	(GMT+03:00) Baghdad
					49	(GMT+03:30) Tehran
					50	(GMT+04:00) Moscow, St. Petersburg
					51	(GMT+04:00) Volgograd
					52	(GMT+04:00) Abu Dhabi, Muscat
					53	(GMT+04:00) Baku, Tbilisi, Yerevan
					54	(GMT+04:30) Kabul
					55	(GMT+05:00) Islamabad, Karachi, Tashkent
					56	(GMT+05:30) Calcutta, Chennai
					57	(GMT+05:30) Mumbai, New Delhi
					58	(GMT+05:30) Sri Jayawardenepura
					59	(GMT+05:45) Kathmandu
					60	(GMT+06:00) Almaty
					61	(GMT+06:00) Yekaterinburg
					62	(GMT+06:00) Astana, Dhaka
					63	(GMT+06:30) Rangoon
					64	(GMT+07:00) Bangkok, Hanoi, Jakarta, Novosibirsk
					65	(GMT+08:00) Krasnoyarsk
					66	(GMT+08:00) Beijing, Hong Kong
					67	(GMT+08:00) Chongqing, Urumqi
					68	(GMT+08:00) Kuala Lumpur, Singapore
					69	(GMT+08:00) Taipei
					70	(GMT+08:00) Perth
					71	(GMT+08:00) Ulaan Bataar
					72	(GMT+09:00) Irkutsk, Seoul
					73	(GMT+09:00) Osaka, Sapporo, Tokyo
					74	(GMT+09:30) Darwin
					75	(GMT+09:30) Adelaide
					76	(GMT+10:00) Yakutsk
					77	(GMT+10:00) Canberra, Melbourne, Sydney
					78	(GMT+10:00) Brisbane
					79	(GMT+10:00) Hobart
					80	(GMT+10:00) Guam, Port Moresby
					81	(GMT+11:00) Vladivostok
					82	(GMT+11:00) Solomon Is.
					83	(GMT+11:00) New Caledonia
					84	(GMT+12:00) Magadan, Fiji, Kamchatka, Marshall Is.
					85	(GMT+12:00) Auckland, Wellington
					86	(GMT+13:00) Nuku'alofa
		                        "
				::= { miscellaneous 3 }

	manuallySetDaylightSaveingTime		OBJECT-TYPE
				SYNTAX INTEGER { yes(1), no(2) }
				MAX-ACCESS read-write
				STATUS current
				DESCRIPTION
					"Manually set the daylight saving time."
				::= { miscellaneous 4 }

	dstStartTimeMonth	OBJECT-TYPE
				SYNTAX INTEGER { mJanuary(1), mFebruary(2), mMarch(3), mApril(4), mMay(5), mJune(6), mJuly(7), mAugust(8), mSeptember(9), mOctober(10), mNovember(11), mDecember(12) }
                MAX-ACCESS read-write
				STATUS current
				DESCRIPTION
					"The month of DST start time."
				::= { miscellaneous 5 }

	dstStartTimeWeek	OBJECT-TYPE
				SYNTAX INTEGER ( 1..5 )              
                MAX-ACCESS read-write
				STATUS current
				DESCRIPTION
					"The week of DST start time."
				::= { miscellaneous 6 }

	dstStartTimeWeekday	OBJECT-TYPE
				SYNTAX INTEGER ( 0..6 )              
                MAX-ACCESS read-write
				STATUS current
				DESCRIPTION
					"The weekday of DST start time."
				::= { miscellaneous 7 }

	dstStartTimeHour	OBJECT-TYPE
				SYNTAX INTEGER ( 0..23 )              
                MAX-ACCESS read-write
				STATUS current
				DESCRIPTION
					"The hour of DST start time."
				::= { miscellaneous 8 }

	dstEndTimeMonth	OBJECT-TYPE
				SYNTAX INTEGER { mJanuary(1), mFebruary(2), mMarch(3), mApril(4), mMay(5), mJune(6), mJuly(7), mAugust(8), mSeptember(9), mOctober(10), mNovember(11), mDecember(12) }
                MAX-ACCESS read-write
				STATUS current
				DESCRIPTION
					"The month of DST end time."
				::= { miscellaneous 9 }

	dstEndTimeWeek	OBJECT-TYPE
				SYNTAX INTEGER ( 1..5 )              
                MAX-ACCESS read-write
				STATUS current
				DESCRIPTION
					"The week of DST end time."
				::= { miscellaneous 10 }

	dstEndTimeWeekday	OBJECT-TYPE
				SYNTAX INTEGER ( 0..6 )              
                MAX-ACCESS read-write
				STATUS current
				DESCRIPTION
					"The weekday of DST end time."
				::= { miscellaneous 11 }

	dstEndTimeHour	OBJECT-TYPE
				SYNTAX INTEGER ( 0..23 )              
                                MAX-ACCESS read-write
				STATUS current
				DESCRIPTION
					"The hour of DST end time."
				::= { miscellaneous 12 }

	ntpServer	OBJECT-TYPE
				SYNTAX OCTET STRING ( SIZE (1..256) )
				MAX-ACCESS read-write
				STATUS current
				DESCRIPTION
					"To synchronize your system time with NTP Server."
				::= { miscellaneous 13 }

	enableTelnet	OBJECT-TYPE
				SYNTAX INTEGER { yes(1), no(2) }
				MAX-ACCESS read-write
				STATUS current
				DESCRIPTION ""
				::= { miscellaneous 14 }

	authenticationMethod	OBJECT-TYPE
				SYNTAX INTEGER { http(1), https(2), both(3) }
				MAX-ACCESS read-write
				STATUS current
				DESCRIPTION ""
				::= { miscellaneous 15 }

	httpsLanPort		OBJECT-TYPE
				SYNTAX INTEGER
				MAX-ACCESS read-write
				STATUS current
				DESCRIPTION ""
				::= { miscellaneous 16 }

	enableWebAccessfromWAN	OBJECT-TYPE
				SYNTAX INTEGER { yes(1), no(2) }
				MAX-ACCESS read-write
				STATUS current
				DESCRIPTION
					"This feature allows you to configure the wireless router via the Internet. The default 
					port is 8080 and you can use http://[WAN IP]:8080 or http://[DDNS name]:8080 to launch 
					the wireless router's web user interface."
				::= { miscellaneous 17 }

	httpPortWebAccessfromWAN	OBJECT-TYPE
				SYNTAX INTEGER  (1024..65535)
				MAX-ACCESS read-write
				STATUS current
				DESCRIPTION 
					"To specify the port used to config RT-AC66U from the Internet( 1024:65535 )."
				::= { miscellaneous 18 }

	httpsPortWebAccessfromWAN	OBJECT-TYPE
				SYNTAX INTEGER  (1024..65535)
				MAX-ACCESS read-write
				STATUS current
				DESCRIPTION 
					"To specify the port used to config RT-AC66U from the Internet( 1024:65535 )."
				::= { miscellaneous 19 }   
				
	autoLogout	OBJECT-TYPE
				SYNTAX INTEGER  (0..999)
				MAX-ACCESS read-write
				STATUS current
				DESCRIPTION 
					"Time to logout automatically. 0 means to disable the function of auto logout. "
				::= { miscellaneous 20 }				

	onlyAllowSpecificIP	OBJECT-TYPE
				SYNTAX INTEGER { yes(1), no(2) }
				MAX-ACCESS read-write
				STATUS current
				DESCRIPTION ""
				::= { miscellaneous 21 }

	mScanClientListAct	OBJECT-TYPE
				SYNTAX INTEGER { scan(1), nothing(2) }
				MAX-ACCESS read-write
				STATUS current
				DESCRIPTION ""
				::= { miscellaneous 22 }


	mScanClientTable	OBJECT-TYPE
				SYNTAX SEQUENCE OF MScanClientEntry
				MAX-ACCESS not-accessible
				STATUS current
				DESCRIPTION ""
                ::= { miscellaneous 23 }

	mScanClientEntry	OBJECT-TYPE
				SYNTAX MScanClientEntry
				MAX-ACCESS not-accessible
				STATUS current
				DESCRIPTION ""
				INDEX { mScanClientIndex }
				::= { mScanClientTable 1 }

 	MScanClientEntry ::= SEQUENCE {
        	mScanClientIndex    	INTEGER,
        	mScanClientIPAddr	    IpAddress,
        	mScanClientName			OCTET STRING
    	}

	mScanClientIndex	OBJECT-TYPE
				SYNTAX INTEGER ( 1..32 )
				MAX-ACCESS not-accessible
				STATUS current
				DESCRIPTION
					"Client entry index."
				::= { mScanClientEntry 1 }

	mScanClientIPAddr	OBJECT-TYPE
				SYNTAX IpAddress
				MAX-ACCESS read-only
				STATUS current
				DESCRIPTION
					"MAC address of the client list."
				::= { mScanClientEntry 2 }

	mScanClientName		OBJECT-TYPE
				SYNTAX OCTET STRING
				MAX-ACCESS read-only
				STATUS current
				DESCRIPTION
					"Name of the client list."
				::= { mScanClientEntry 3 }

	mClientListTable	OBJECT-TYPE
				SYNTAX SEQUENCE OF MClientListEntry
				MAX-ACCESS not-accessible
				STATUS current
				DESCRIPTION
					"Specified IP address list."
				::= { miscellaneous 24 }

	mClientListEntry	OBJECT-TYPE
				SYNTAX MClientListEntry
				MAX-ACCESS not-accessible
				STATUS current
				DESCRIPTION ""
				INDEX { mClientListIndex }
				::= { mClientListTable 1 }

 	MClientListEntry ::= SEQUENCE {
        	mClientListIndex		INTEGER,
			mClientListClient		IpAddress,
        	mClientListDelEntry		INTEGER
    	}
    
	mClientListIndex	OBJECT-TYPE
				SYNTAX INTEGER ( 1..4 )
				MAX-ACCESS not-accessible
				STATUS current
				DESCRIPTION 
					"Client Index."
				::= { mClientListEntry 1 }

	mClientListClient	OBJECT-TYPE
				SYNTAX 	IpAddress
				MAX-ACCESS read-write
				STATUS current
				DESCRIPTION
					"IP address of client list."
				::= { mClientListEntry 2 }

	mClientListDelEntry	OBJECT-TYPE
				SYNTAX INTEGER { yes(1), no(2) }
				MAX-ACCESS read-write
				STATUS current
				DESCRIPTION
					"Delete the specified IP client entry."
				::= { mClientListEntry 3 }

-- **********************************************************************
-- *  End of System Config Section 
-- **********************************************************************

-- **********************************************************************
-- *  Firmware Upgrade Section 
-- **********************************************************************

	firmware-upgrade	OBJECT IDENTIFIER ::= { administration 3 }

	fTftpSrv	OBJECT-TYPE
				SYNTAX OCTET STRING ( SIZE (0..39) )
				MAX-ACCESS read-write
				STATUS current
				DESCRIPTION
					"Tftp server ip."
                                ::= { firmware-upgrade 1 }

	fTftpFile	OBJECT-TYPE
				SYNTAX OCTET STRING
				MAX-ACCESS read-write
				STATUS current
				DESCRIPTION
					"The file name of the firmware which will be uploaded to the device."
				::= { firmware-upgrade 2 }

	fFirmwareUpgrade	OBJECT-TYPE
				SYNTAX INTEGER { upgrade(1), nothing(2) }
				MAX-ACCESS read-write
				STATUS current
				DESCRIPTION
					"Upgrade firmware or not. When the firmware upgrading, please don't power off the device, 
					and wait for 80 seconds to reconnect to device."
				::= { firmware-upgrade 3 }

-- **********************************************************************
-- *  End of Firmware Upgrade Config Section 
-- **********************************************************************

-- **********************************************************************
-- *  Restore/Save/Upload Setting Section 
-- **********************************************************************

	setting-management	OBJECT IDENTIFIER ::= { administration 4 }

	sTftpSrv	OBJECT-TYPE
				SYNTAX OCTET STRING ( SIZE (0..39) )
				MAX-ACCESS read-write
				STATUS current
				DESCRIPTION
					"Tftp server ip."
				::= { setting-management 1 }

	sTftpFile	OBJECT-TYPE
				SYNTAX OCTET STRING
				MAX-ACCESS read-write
				STATUS current
				DESCRIPTION
					"The file name of the config file which will be uploaded to the device or downloaded to the 
					local PC."
				::= { setting-management 2 }

	sTftpAction	OBJECT-TYPE
				SYNTAX INTEGER { get(1), put(2), nothing(3) }
				MAX-ACCESS read-write
				STATUS current
				DESCRIPTION
					"The actions of tftp. 'Get' will get config file from remote PC to device, and 'Put' will 
					upload config file from device to remote PC."
				::= { setting-management 3 }

-- **********************************************************************
-- *  End of Restore/Save/Upload Setting Config Section 
-- **********************************************************************

-- **********************************************************************
-- *  SNMP Setup Section
-- **********************************************************************

	snmp-setup	OBJECT IDENTIFIER ::= { administration 5 }     
	
	snmpEnable	OBJECT-TYPE
				SYNTAX INTEGER { yes(1), no(2) }
				MAX-ACCESS read-write
				STATUS current
				DESCRIPTION
					"Enable SNMP."
				::= { snmp-setup 1 }

	
	snSystemName	OBJECT-TYPE
				SYNTAX OCTET STRING ( SIZE (0..255) )
				MAX-ACCESS read-write
				STATUS current
				DESCRIPTION
					"The value of this object is the system name of the device. This value will be seen in the 
					remote SNMP agent discovery result, and can be gotten and set by MIB browser and WEB."
				::= { snmp-setup 2 }

	snLocation	OBJECT-TYPE
				SYNTAX OCTET STRING ( SIZE (0..255) )
				MAX-ACCESS read-write
				STATUS current
				DESCRIPTION
					"The value of this object is the system location of the device. This value will be seen in 
					the remote SNMP agent discovery result, and can be gotten and set by MIB browser and WEB."
				::= { snmp-setup 3 }

	snContact	OBJECT-TYPE
				SYNTAX OCTET STRING ( SIZE (0..255) )
				MAX-ACCESS read-write
				STATUS current
				DESCRIPTION
					"The value of this object is the system contact information of the device. This value will 
					be seen in the remote SNMP agent discovery result, and can be gotten and set by MIB browser 
					and WEB."
				::= { snmp-setup 4 }	
                                
	snGetCommunity		OBJECT-TYPE
				SYNTAX OCTET STRING
				MAX-ACCESS read-write
				STATUS current
				DESCRIPTION
					"The value of this object is the read-write community used in the SNMPv1 and SNMPv2c. The 
					community string can be gotten and set by MIB browser and WEB."
				::= { snmp-setup 5 }

	snSetCommunity		OBJECT-TYPE
				SYNTAX OCTET STRING
				MAX-ACCESS read-write
				STATUS current
				DESCRIPTION
					"The value of this object is the read-only community used in the SNMPv1 and SNMPv2c. The 
					community string can be gotten and set by MIB browser and WEB."
				::= { snmp-setup 6 }

	snmpV3Setting	OBJECT IDENTIFIER ::= { snmp-setup 7 }

	authProtocol	OBJECT-TYPE
				SYNTAX INTEGER { none(1), md5(2), sha(3) }
				MAX-ACCESS read-write
				STATUS current
				DESCRIPTION
					"The value of this object shows SNMPv3 authentication protocol."
				::= { snmpV3Setting 1 }

	authPass	OBJECT-TYPE
				SYNTAX OCTET STRING ( SIZE (8..64) )
				MAX-ACCESS read-write
				STATUS current
				DESCRIPTION
					"The authentication password. SNMPv3 pass phrases must be at least 8 characters long."
				::= { snmpV3Setting 2 }

	privProtocol	OBJECT-TYPE
				SYNTAX INTEGER { none(1), des(2), aes(3) }
				MAX-ACCESS read-write
				STATUS current
				DESCRIPTION
					"The value of this object shows SNMPv3 privacy protocol."
				::= { snmpV3Setting 3 }

	privPass	OBJECT-TYPE
				SYNTAX OCTET STRING ( SIZE (8..64) )
				MAX-ACCESS read-write
				STATUS current
				DESCRIPTION
					"The privacy password. SNMPv3 passphrases must be at least 8 characters long."
				::= { snmpV3Setting 4 }

	snVersion	OBJECT-TYPE
				SYNTAX OCTET STRING
				MAX-ACCESS read-only
				STATUS current
				DESCRIPTION
					"The value of this object is the MIB version device supports."
				::= { snmp-setup 8 }

-- **********************************************************************
-- *  End of SNMP Setup Section 
-- **********************************************************************

-- **********************************************************************
-- *  System Command Section
-- **********************************************************************
	systemCommand	OBJECT-TYPE
				SYNTAX INTEGER { commit(1), reboot(2), factoryDefault(3), restart-wireless(4), restart-net-and-phy(5), restart-net(6), restart-wan-if(7),
				                restart-firewall(8), restart-ddns(9), restart-pppoe-relay(10), restart-allnet(11), restart-pptpd(12), restart-all(13), 
				                restart-time(14), restart-qos(15), restart-upnp(16), restart-ntpc(17), restart-snmpd(18), wps-apply(19), reset-wps(20),
				                nothing(21)}
				MAX-ACCESS read-write
				STATUS current
				DESCRIPTION
					"
					1	commit
					2	reboot
					3	factoryDefault
					4	restart_wireless
					5	restart_net_and_phy
					6	restart_net
					7	restart_wan_if
					8	restart_firewall
					9	restart_ddns
					10	restart_pppoe_relay
					11	restart_allnet
					12	restart_pptpd
					13	restart_all
					14	restart_time
					15	restart_qos
					16	restart_upnp
					17	restart_ntpc
					18	restart_snmpd
					19	wps_apply
					20	reset_wps
					21	nothing
					"                                         
                    ::= { administration 6 }   			
    			                                     
-- **********************************************************************
-- *  End of System Command Section 
-- **********************************************************************

-- ======================================================================
-- * End of Administration Section
-- ======================================================================





-- ======================================================================
-- * System Log Section
-- ======================================================================

-- **********************************************************************
-- *  General Log Section 
-- **********************************************************************

	general-log	OBJECT IDENTIFIER ::= { systemLog 1 }

	systemTime	OBJECT-TYPE
				SYNTAX OCTET STRING
				MAX-ACCESS read-only
				STATUS current
				DESCRIPTION
					""
				::= { general-log 1 }

	upTime		OBJECT-TYPE
				SYNTAX TimeTicks
				MAX-ACCESS read-only
				STATUS current
				DESCRIPTION
					"The value of this oject is the elapsed time (in hundredths of a second) since system boot."
				::= { general-log 2 }    
				
	saveSysLog	OBJECT IDENTIFIER ::= { general-log 3 }
	
	sysLogTftpSrv	OBJECT-TYPE
				SYNTAX OCTET STRING ( SIZE (0..39) )
				MAX-ACCESS read-write
				STATUS current
				DESCRIPTION
					"Tftp server ip."
				::= { saveSysLog 1 }

	sysLogTftpFile	OBJECT-TYPE
				SYNTAX OCTET STRING
				MAX-ACCESS read-write
				STATUS current
				DESCRIPTION
					"The file name of the syslog file which will be saved to the 
					local PC. Default name is syslog.txt."
				::= { saveSysLog 2 }

	sysLogSaveAct	OBJECT-TYPE
				SYNTAX INTEGER { save(1), nothing(2) }
				MAX-ACCESS read-write
				STATUS current
				DESCRIPTION
					"Select 'Save' to save syslog file to the local PC. "
				::= { saveSysLog 3 }
				
-- **********************************************************************
-- *  End of General Log Config Section 
-- **********************************************************************


-- **********************************************************************
-- * Wireless Log Section 
-- **********************************************************************

	wireless-log	OBJECT IDENTIFIER ::= { systemLog 2 }

	logWl2g		OBJECT IDENTIFIER ::= { wireless-log 1 }

	bssInfoWl2g	OBJECT-TYPE
				SYNTAX OCTET STRING
				MAX-ACCESS read-only
				STATUS current
				DESCRIPTION
					"The value of this object shows the bss info of the device."
                ::= { logWl2g 1 } 

	wl2gRefreshSta	OBJECT-TYPE
				SYNTAX INTEGER { refresh(1), nothing(2) }
				MAX-ACCESS read-write
				STATUS current
				DESCRIPTION
					"Get/Refresh station table of wireless 2g."
				::= { logWl2g 2 }

	wl2gStationTable	OBJECT-TYPE
				SYNTAX SEQUENCE OF Wl2gStationEntry
				MAX-ACCESS not-accessible
				STATUS current
				DESCRIPTION
					"2.4G station list."
                ::= { logWl2g 3 }
                                    
	wl2gStationEntry	OBJECT-TYPE
				SYNTAX Wl2gStationEntry
				MAX-ACCESS not-accessible
				STATUS current
				DESCRIPTION ""
				INDEX { wl2gStationIndex }
				::= { wl2gStationTable 1 }

 	Wl2gStationEntry ::= SEQUENCE {
        	wl2gStationIndex	INTEGER,
        	wl2gStationMACAddr	OCTET STRING,
        	wl2gAssociated		OCTET STRING, 
        	wl2gAuthorized		OCTET STRING,   
        	wl2gRSSI			OCTET STRING,
        	wl2gPSM             OCTET STRING,
        	wl2gTxRate			OCTET STRING,
        	wl2gRxRate			OCTET STRING,         
        	wl2gStationConnectTime  TimeTicks
    	}                           
    
	wl2gStationIndex	OBJECT-TYPE
                SYNTAX INTEGER ( 1..64 )
                MAX-ACCESS not-accessible
                STATUS current
                DESCRIPTION 
                	"2.4G Station List Index"
                ::= { wl2gStationEntry 1 }

	wl2gStationMACAddr	OBJECT-TYPE
				SYNTAX OCTET STRING
				MAX-ACCESS read-only
				STATUS current
				DESCRIPTION
					"The MAC address of 2.4G station."
                ::= { wl2gStationEntry  2 } 	
                                
	wl2gAssociated	OBJECT-TYPE
				SYNTAX OCTET STRING
				MAX-ACCESS read-only
				STATUS current
				DESCRIPTION
					"Show the associated state of 2.4G station."
				::= { wl2gStationEntry 3 }   
				
	wl2gAuthorized	OBJECT-TYPE
				SYNTAX OCTET STRING
				MAX-ACCESS read-only
				STATUS current
				DESCRIPTION
					"Show the authorized state of 2.4G station."
				::= { wl2gStationEntry 4 } 

	wl2gRSSI	OBJECT-TYPE
				SYNTAX OCTET STRING
				MAX-ACCESS read-only
				STATUS current
				DESCRIPTION
					"Show the RSSI(dBm) of 2.4G station."
				::= { wl2gStationEntry 5 } 
				
	wl2gPSM		OBJECT-TYPE
				SYNTAX OCTET STRING
				MAX-ACCESS read-only
				STATUS current
				DESCRIPTION
					"Show the PSM of 2.4G station."
				::= { wl2gStationEntry 6 } 					
				
	wl2gTxRate	OBJECT-TYPE
				SYNTAX OCTET STRING
				MAX-ACCESS read-only
				STATUS current
				DESCRIPTION
					"The Tx Rate of 2.4G station."
                ::= { wl2gStationEntry  7 }    
                
	wl2gRxRate	OBJECT-TYPE
				SYNTAX OCTET STRING
				MAX-ACCESS read-only
				STATUS current
				DESCRIPTION
					"The Rx Rate of 2.4G station."
				::= { wl2gStationEntry  8 }
                			                                				
	wl2gStationConnectTime	OBJECT-TYPE
				SYNTAX TimeTicks
				MAX-ACCESS read-only
				STATUS current
				DESCRIPTION
					"The value of this oject is the elapsed time (in hundredths of a second) 
					since the 2.4G station connects to RT-AC66U."
				::= { wl2gStationEntry 9 }  
				

	logWl5g		OBJECT IDENTIFIER ::= { wireless-log 2 }

	bssInfoWl5g	OBJECT-TYPE
				SYNTAX OCTET STRING
				MAX-ACCESS read-only
				STATUS current
				DESCRIPTION
					"The value of this object shows the bss info of the device."
                ::= { logWl5g 1 }

	wl5gRefreshSta	OBJECT-TYPE
				SYNTAX INTEGER { refresh(1), nothing(2) }
				MAX-ACCESS read-write
				STATUS current
				DESCRIPTION
					"Get/Refresh station table of wireless 5g."
				::= { logWl5g 2 }

	wl5gStationTable	OBJECT-TYPE
				SYNTAX SEQUENCE OF Wl5gStationEntry
				MAX-ACCESS not-accessible
				STATUS current
				DESCRIPTION
					"5G station list."
                ::= { logWl5g 3 }
                                    
	wl5gStationEntry	OBJECT-TYPE
				SYNTAX Wl5gStationEntry
				MAX-ACCESS not-accessible
				STATUS current
				DESCRIPTION ""
				INDEX { wl5gStationIndex }
				::= { wl5gStationTable 1 }

 	Wl5gStationEntry ::= SEQUENCE {
        	wl5gStationIndex	INTEGER,
        	wl5gStationMACAddr	OCTET STRING,
        	wl5gAssociated		OCTET STRING, 
        	wl5gAuthorized		OCTET STRING,   
        	wl5gRSSI			OCTET STRING,
        	wl5gPSM             OCTET STRING,
        	wl5gTxRate			OCTET STRING,
        	wl5gRxRate			OCTET STRING,         
        	wl5gStationConnectTime  TimeTicks
    	}                              
    
	wl5gStationIndex	OBJECT-TYPE
				SYNTAX INTEGER ( 1..64 )
                MAX-ACCESS not-accessible
                STATUS current
                DESCRIPTION 
                   	"5G Station List Index"
                ::= { wl5gStationEntry 1 }

	wl5gStationMACAddr	OBJECT-TYPE
				SYNTAX OCTET STRING
				MAX-ACCESS read-only
				STATUS current
				DESCRIPTION
					"The MAC address of 5G station list."
                ::= { wl5gStationEntry  2 } 	
                                
	wl5gAssociated	OBJECT-TYPE
				SYNTAX OCTET STRING
				MAX-ACCESS read-only
				STATUS current
				DESCRIPTION
					"Show the associated state of 2.4G station."
				::= { wl5gStationEntry 3 }   
				
	wl5gAuthorized	OBJECT-TYPE
				SYNTAX OCTET STRING
				MAX-ACCESS read-only
				STATUS current
				DESCRIPTION
					"Show the authorized state of 2.4G station."
				::= { wl5gStationEntry 4 } 

	wl5gRSSI	OBJECT-TYPE
				SYNTAX OCTET STRING
				MAX-ACCESS read-only
				STATUS current
				DESCRIPTION
					"Show the RSSI(dBm) of 2.4G station."
				::= { wl5gStationEntry 5 } 
				
	wl5gPSM		OBJECT-TYPE
				SYNTAX OCTET STRING
				MAX-ACCESS read-only
				STATUS current
				DESCRIPTION
					"Show the PSM of 2.4G station."
				::= { wl5gStationEntry 6 } 					
				
	wl5gTxRate	OBJECT-TYPE
				SYNTAX OCTET STRING
				MAX-ACCESS read-only
				STATUS current
				DESCRIPTION
					"The Tx Rate of 2.4G station."
                ::= { wl5gStationEntry  7 }    
                
	wl5gRxRate	OBJECT-TYPE
				SYNTAX OCTET STRING
				MAX-ACCESS read-only
				STATUS current
				DESCRIPTION
					"The Rx Rate of 2.4G station."
				::= { wl5gStationEntry  8 }
                			                                				
	wl5gStationConnectTime	OBJECT-TYPE
				SYNTAX TimeTicks
				MAX-ACCESS read-only
				STATUS current
				DESCRIPTION
					"The value of this oject is the elapsed time (in hundredths of a second) 
					since the 2.4G station connects to RT-AC66U."
				::= { wl5gStationEntry 9 }  

-- **********************************************************************
-- *  End of Wireless Log Section 
-- **********************************************************************

-- **********************************************************************
-- * DHCP leases Section 
-- **********************************************************************

	dhcp-leases		OBJECT IDENTIFIER ::= { systemLog 3 }

	dhcpLeasesTable	OBJECT-TYPE
               SYNTAX SEQUENCE OF DhcpLeasesEntry
               MAX-ACCESS not-accessible
               STATUS current
               DESCRIPTION
               		"DHCP leases list."
               ::= { dhcp-leases 1 }

	dhcpLeasesEntry		OBJECT-TYPE
				SYNTAX DhcpLeasesEntry
				MAX-ACCESS not-accessible
				STATUS current
				DESCRIPTION ""
				INDEX { dhcpLeasesIndex }
				::= { dhcpLeasesTable 1 }

 	DhcpLeasesEntry ::= SEQUENCE {
			dhcpLeasesIndex		INTEGER, 
			dhcpLeasesHostName	OCTET STRING,
			dhcpLeasesIPAddr	OCTET STRING, 
			dhcpLeasesMACAddr	OCTET STRING,
			dhcpLeasesExpires	OCTET STRING
    	}                           
    
	dhcpLeasesIndex		OBJECT-TYPE
				SYNTAX INTEGER	(1..253)
				MAX-ACCESS not-accessible
				STATUS current
				DESCRIPTION
					"DHCP Leases List Index."
				::= { dhcpLeasesEntry 1 }

 	dhcpLeasesHostName	OBJECT-TYPE
				SYNTAX OCTET STRING
				MAX-ACCESS read-only
				STATUS current
				DESCRIPTION
					"The host name of DHCP leases list."
				::= { dhcpLeasesEntry 2 }     
				
	dhcpLeasesIPAddr	OBJECT-TYPE
				SYNTAX OCTET STRING
				MAX-ACCESS read-only
				STATUS current
				DESCRIPTION
					"The IP address of DHCP leases list."
				::= { dhcpLeasesEntry 3 }				

	dhcpLeasesMACAddr	OBJECT-TYPE
				SYNTAX OCTET STRING
				MAX-ACCESS read-only
				STATUS current
				DESCRIPTION
					"The MAC address of DHCP leases list."
				::= { dhcpLeasesEntry 4 }
				   
	dhcpLeasesExpires	OBJECT-TYPE
				SYNTAX OCTET STRING
				MAX-ACCESS read-only
				STATUS current
				DESCRIPTION
					"The expires of DHCP leases list."
				::= { dhcpLeasesEntry 5 }				

-- **********************************************************************
-- *  End of DHCP leases Section 
-- **********************************************************************
      
	ipv6-log	OBJECT IDENTIFIER ::= { systemLog 4 }  
	
	ipv6ConnectionType OBJECT-TYPE
				SYNTAX OCTET STRING
				MAX-ACCESS read-only
				STATUS current
				DESCRIPTION
					"IPv6 Connection Type."
				::= { ipv6-log 1 }     	

	ipv6WanAddress OBJECT-TYPE
				SYNTAX OCTET STRING
				MAX-ACCESS read-only
				STATUS current
				DESCRIPTION
					"WAN IPv6 Address."
				::= { ipv6-log 2 }  

	ipv6WanGateway OBJECT-TYPE
				SYNTAX OCTET STRING
				MAX-ACCESS read-only
				STATUS current
				DESCRIPTION
					"WAN IPv6 Gateway."
				::= { ipv6-log 3 } 
												
	ipv6LanAddress OBJECT-TYPE
				SYNTAX OCTET STRING
				MAX-ACCESS read-only
				STATUS current
				DESCRIPTION
					"LAN IPv6 Address."
				::= { ipv6-log 4 }  			

	ipv6LanLinkLocalAddress OBJECT-TYPE
				SYNTAX OCTET STRING
				MAX-ACCESS read-only
				STATUS current
				DESCRIPTION
					"LAN IPv6 Link-Local Address."
				::= { ipv6-log 5 }
																	
	ipv6DhcpPd  OBJECT-TYPE
				SYNTAX OCTET STRING
				MAX-ACCESS read-only
				STATUS current
				DESCRIPTION
					"DHCP-PD."
				::= { ipv6-log 6 }          
				
	ipv6LanPrefix  OBJECT-TYPE
				SYNTAX OCTET STRING
				MAX-ACCESS read-only
				STATUS current
				DESCRIPTION
					"LAN IPv6 Prefix."
				::= { ipv6-log 7 }     
				
	ipv6DnsAddress  OBJECT-TYPE
				SYNTAX OCTET STRING
				MAX-ACCESS read-only
				STATUS current
				DESCRIPTION
					"DNS Address."
				::= { ipv6-log 8 }				
																					
   	ipv6LanDevicesTable	OBJECT-TYPE
				SYNTAX SEQUENCE OF Ipv6LanDeviceEntry
               	MAX-ACCESS not-accessible
               	STATUS current
               	DESCRIPTION
               		"IPv6 LAN devices list."
               	::= { ipv6-log 9 }

	ipv6LanDeviceEntry		OBJECT-TYPE
				SYNTAX Ipv6LanDeviceEntry
				MAX-ACCESS not-accessible
				STATUS current
				DESCRIPTION ""
				INDEX { ipv6LanDeviceIndex }
				::= { ipv6LanDevicesTable 1 }

 	Ipv6LanDeviceEntry ::= SEQUENCE {
			ipv6LanDeviceIndex		INTEGER, 
			ipv6LanDeviceHostName	OCTET STRING,
			ipv6LanDeviceMACAddr	OCTET STRING,
			ipv6LanDeviceIPv6Addr	OCTET STRING 
    	}                           
    
	ipv6LanDeviceIndex		OBJECT-TYPE
				SYNTAX INTEGER (1..253)
				MAX-ACCESS not-accessible
				STATUS current
				DESCRIPTION
					"IPv6 LAN Devices Index."
				::= { ipv6LanDeviceEntry 1 }

 	ipv6LanDeviceHostName	OBJECT-TYPE
				SYNTAX OCTET STRING
				MAX-ACCESS read-only
				STATUS current
				DESCRIPTION
					"The host name of IPv6 LAN device."
				::= { ipv6LanDeviceEntry 2 }     				

	ipv6LanDeviceMACAddr	OBJECT-TYPE
				SYNTAX OCTET STRING
				MAX-ACCESS read-only
				STATUS current
				DESCRIPTION
					"The MAC address of IPv6 LAN device."
				::= { ipv6LanDeviceEntry 3 } 
				
	ipv6LanDeviceIPv6Addr	OBJECT-TYPE
				SYNTAX OCTET STRING
				MAX-ACCESS read-only
				STATUS current
				DESCRIPTION
					"The IPv6 address of IPv6 LAN device."
				::= { ipv6LanDeviceEntry 4 }							

-- **********************************************************************
-- * IPv6 Log Section 
-- **********************************************************************


-- **********************************************************************
-- *  End of IPv6 Log Section 
-- **********************************************************************

-- **********************************************************************
-- * Routing Table Section 
-- **********************************************************************

	routing-table	OBJECT IDENTIFIER ::= { systemLog 5 }
	
	routingTable	OBJECT-TYPE
				SYNTAX SEQUENCE OF RoutingEntry
                MAX-ACCESS not-accessible
                STATUS current
                DESCRIPTION
                	"Routing list."
                ::= { routing-table 1 }

	routingEntry	OBJECT-TYPE
				SYNTAX RoutingEntry
				MAX-ACCESS not-accessible
				STATUS current
				DESCRIPTION ""
				INDEX { routingIndex }
				::= { routingTable 1 }

 	RoutingEntry ::= SEQUENCE {
				routingIndex		INTEGER,
				routingDestination	OCTET STRING,
				routingGateway		OCTET STRING,
				routingGenmask		OCTET STRING,
				routingFlags		OCTET STRING,
				routingMetric		INTEGER,
				routingRef			INTEGER,
				routingUse			INTEGER,
				routingIface		OCTET STRING
    	}                           
    
	routingIndex	OBJECT-TYPE
				SYNTAX INTEGER	(1..64)
				MAX-ACCESS not-accessible
				STATUS current
				DESCRIPTION
					"Routing rule Index."
				::= { routingEntry 1 }

	routingDestination	OBJECT-TYPE
				SYNTAX OCTET STRING
				MAX-ACCESS read-only
				STATUS current
				DESCRIPTION
					"The destination of routing rule."
				::= { routingEntry 2 }

	routingGateway	OBJECT-TYPE
				SYNTAX OCTET STRING
				MAX-ACCESS read-only
				STATUS current
				DESCRIPTION
					"The gateway of routing rule."
				::= { routingEntry 3 }

	routingGenmask	OBJECT-TYPE
				SYNTAX OCTET STRING
				MAX-ACCESS read-only
				STATUS current
				DESCRIPTION
					"The genmask of routing rule."
				::= { routingEntry 4 }

	routingFlags	OBJECT-TYPE
				SYNTAX OCTET STRING
				MAX-ACCESS read-only
				STATUS current
				DESCRIPTION
					"The flags of routing rule."
				::= { routingEntry 5 }

	routingMetric	OBJECT-TYPE
				SYNTAX INTEGER
				MAX-ACCESS read-only
				STATUS current
				DESCRIPTION
					"The metric of routing rule."
				::= { routingEntry 6 }

	routingRef	OBJECT-TYPE
				SYNTAX INTEGER
				MAX-ACCESS read-only
				STATUS current
				DESCRIPTION
					"The ref of routing rule."
				::= { routingEntry 7 }

	routingUse	OBJECT-TYPE
				SYNTAX INTEGER
				MAX-ACCESS read-only
				STATUS current
				DESCRIPTION
					"The use of routing rule."
				::= { routingEntry 8 }

	routingIface	OBJECT-TYPE
				SYNTAX OCTET STRING
				MAX-ACCESS read-only
				STATUS current
				DESCRIPTION
					"The Iface of routing rule."
				::= { routingEntry 9 }

	ipv6RoutingTable	OBJECT-TYPE
				SYNTAX SEQUENCE OF Ipv6RoutingEntry
                MAX-ACCESS not-accessible
                STATUS current
                DESCRIPTION
                	"IPv6 Routing table."
                ::= { routing-table 2 }

	ipv6RoutingEntry	OBJECT-TYPE
				SYNTAX Ipv6RoutingEntry
				MAX-ACCESS not-accessible
				STATUS current
				DESCRIPTION ""
				INDEX { ipv6RoutingIndex }
				::= { ipv6RoutingTable 1 }

 	Ipv6RoutingEntry ::= SEQUENCE {
				ipv6RoutingIndex		INTEGER,
				ipv6RoutingDest			OCTET STRING,
				ipv6RoutingNextHop		OCTET STRING,
				ipv6RoutingFlags		OCTET STRING,
				ipv6RoutingMetric		INTEGER,
				ipv6RoutingRef			INTEGER,
				ipv6RoutingUse			INTEGER,
				ipv6RoutingIface		OCTET STRING
    	}                           
    
	ipv6RoutingIndex	OBJECT-TYPE
				SYNTAX INTEGER (1..64)
				MAX-ACCESS not-accessible
				STATUS current
				DESCRIPTION
					"IPv6 Routing rule Index."
				::= { ipv6RoutingEntry 1 }

	ipv6RoutingDest		OBJECT-TYPE
				SYNTAX OCTET STRING
				MAX-ACCESS read-only
				STATUS current
				DESCRIPTION
					"The destination of IPv6 routing rule."
				::= { ipv6RoutingEntry 2 }

	ipv6RoutingNextHop	OBJECT-TYPE
				SYNTAX OCTET STRING
				MAX-ACCESS read-only
				STATUS current
				DESCRIPTION
					"The gateway of IPv6 routing rule."
				::= { ipv6RoutingEntry 3 }

	ipv6RoutingFlags	OBJECT-TYPE
				SYNTAX OCTET STRING
				MAX-ACCESS read-only
				STATUS current
				DESCRIPTION
					"The flags of IPv6 routing rule."
				::= { ipv6RoutingEntry 4 }

	ipv6RoutingMetric	OBJECT-TYPE
				SYNTAX INTEGER
				MAX-ACCESS read-only
				STATUS current
				DESCRIPTION
					"The metric of IPv6 routing rule."
				::= { ipv6RoutingEntry 5 }

	ipv6RoutingRef	OBJECT-TYPE
				SYNTAX INTEGER
				MAX-ACCESS read-only
				STATUS current
				DESCRIPTION
					"The ref of IPv6 routing rule."
				::= { ipv6RoutingEntry 6 }

	ipv6RoutingUse	OBJECT-TYPE
				SYNTAX INTEGER
				MAX-ACCESS read-only
				STATUS current
				DESCRIPTION
					"The use of IPv6 routing rule."
				::= { ipv6RoutingEntry 7 }

	ipv6RoutingIface	OBJECT-TYPE
				SYNTAX OCTET STRING
				MAX-ACCESS read-only
				STATUS current
				DESCRIPTION
					"The Iface of IPv6 routing rule."
				::= { ipv6RoutingEntry 8 }

-- **********************************************************************
-- *  End of Routing Table Section 
-- **********************************************************************

-- **********************************************************************
-- * Port Forwarding Section 
-- **********************************************************************

	port-forwarding-log	OBJECT IDENTIFIER ::= { systemLog 6 }

	portForwardingLogTable	OBJECT-TYPE
                SYNTAX SEQUENCE OF PortForwardingLogEntry
                MAX-ACCESS not-accessible
                STATUS current
                DESCRIPTION
                	"This table shows the port forwarding status. 
                    Some P2P programs use the UPnP protocol to open
                    the port and the port number is shown on this table."
                ::= { port-forwarding-log 1 }

	portForwardingLogEntry	OBJECT-TYPE
				SYNTAX PortForwardingLogEntry
				MAX-ACCESS not-accessible
				STATUS current
				DESCRIPTION ""
				INDEX { portForwardingLogIndex }
				::= { portForwardingLogTable 1 }

 	PortForwardingLogEntry ::= SEQUENCE {
				portForwardingLogIndex			INTEGER,
				portForwardingLogDestination	OCTET STRING,
				portForwardingLogProtocol		OCTET STRING,
				portForwardingLogPortRange		OCTET STRING,
				portForwardingLogRedirectTo		OCTET STRING,
				portForwardingLogLocalPort		OCTET STRING
    	}
    
	portForwardingLogIndex	OBJECT-TYPE
				SYNTAX INTEGER	(1..32)
				MAX-ACCESS not-accessible
				STATUS current
				DESCRIPTION
					"Port Forwarding List Index."
				::= { portForwardingLogEntry 1 }

	portForwardingLogDestination	OBJECT-TYPE
				SYNTAX OCTET STRING
				MAX-ACCESS read-only
				STATUS current
				DESCRIPTION
					"The destination of port forwarding list."
				::= { portForwardingLogEntry 2 }

	portForwardingLogProtocol		OBJECT-TYPE
				SYNTAX OCTET STRING
				MAX-ACCESS read-only
				STATUS current
				DESCRIPTION
					"The protocol of port forwarding list."
				::= { portForwardingLogEntry 3 }

	portForwardingLogPortRange		OBJECT-TYPE
				SYNTAX OCTET STRING
				MAX-ACCESS read-only
				STATUS current
				DESCRIPTION
					"The port range of port forwarding list."
				::= { portForwardingLogEntry 4 }

	portForwardingLogRedirectTo		OBJECT-TYPE
				SYNTAX OCTET STRING
				MAX-ACCESS read-only
				STATUS current
				DESCRIPTION
					"The redirect of port forwarding list."
				::= { portForwardingLogEntry 5 }

	portForwardingLogLocalPort		OBJECT-TYPE
				SYNTAX OCTET STRING
				MAX-ACCESS read-only
				STATUS current
				DESCRIPTION
					"The local port of port forwarding list."
				::= { portForwardingLogEntry 6 }

-- **********************************************************************
-- *  End of Port Forwarding Section 
-- **********************************************************************
                    
-- **********************************************************************
-- * Connection Section 
-- **********************************************************************                    
                    
	connection-log	OBJECT IDENTIFIER ::= { systemLog 7 }     

	activeConnectionTable	OBJECT-TYPE
                SYNTAX SEQUENCE OF ActiveConnectionEntry
                MAX-ACCESS not-accessible
                STATUS current
                DESCRIPTION
                	"This is the history log of active connections."
                ::= { connection-log 1 }

	activeConnectionEntry	OBJECT-TYPE
				SYNTAX ActiveConnectionEntry
				MAX-ACCESS not-accessible
				STATUS current
				DESCRIPTION ""
				INDEX { activeConnectionIndex }
				::= { activeConnectionTable 1 }

 	ActiveConnectionEntry ::= SEQUENCE {
				activeConnectionIndex			INTEGER,
				activeConnectionProto			OCTET STRING,
				activeConnectionNatedAddr		OCTET STRING,
				activeConnectionDestAddr		OCTET STRING,
				activeConnectionState			OCTET STRING
			}
    
	activeConnectionIndex	OBJECT-TYPE
				SYNTAX INTEGER (1..253)
				MAX-ACCESS not-accessible
				STATUS current
				DESCRIPTION
					"Index of active connection."
				::= { activeConnectionEntry 1 }

	activeConnectionProto	OBJECT-TYPE
				SYNTAX OCTET STRING
				MAX-ACCESS read-only
				STATUS current
				DESCRIPTION
					"Protocol of active connection."
				::= { activeConnectionEntry 2 }

	activeConnectionNatedAddr	OBJECT-TYPE
				SYNTAX OCTET STRING
				MAX-ACCESS read-only
				STATUS current
				DESCRIPTION
					"Nated address of active connection."
				::= { activeConnectionEntry 3 }

	activeConnectionDestAddr	OBJECT-TYPE
				SYNTAX OCTET STRING
				MAX-ACCESS read-only
				STATUS current
				DESCRIPTION
					"Destination address of active connection."
				::= { activeConnectionEntry 4 }

	activeConnectionState	OBJECT-TYPE
				SYNTAX OCTET STRING
				MAX-ACCESS read-only
				STATUS current
				DESCRIPTION
					"State of active connection."
				::= { activeConnectionEntry 5 }	
                    
-- **********************************************************************
-- *  End of Connection Section 
-- **********************************************************************
                    
-- ======================================================================
-- * End of System Log Section
-- ======================================================================




-- ======================================================================
-- * Guest Network Section
-- ======================================================================

-- **********************************************************************
-- *  Guest Network Section 
-- **********************************************************************

-- ++++++++++++++++++++++++++++++++++++++++++++++++++++++++++++++++++++++
-- +  Guest Network Section (2.4G)
-- ++++++++++++++++++++++++++++++++++++++++++++++++++++++++++++++++++++++

	guest-network-wl2g	OBJECT IDENTIFIER ::= { guestNetwork 1 }

	wl2gGuestNetworkTable	OBJECT-TYPE
                                SYNTAX SEQUENCE OF Wl2gGuestNetworkEntry
                                MAX-ACCESS not-accessible
                                STATUS current
                                DESCRIPTION
                                	"Guest network list for 2G."
                                ::= { guest-network-wl2g 1 }
           
	wl2gGuestNetworkEntry	OBJECT-TYPE
				SYNTAX Wl2gGuestNetworkEntry
				MAX-ACCESS not-accessible
				STATUS current
				DESCRIPTION ""
				INDEX { gIndexWl2g }
				::= { wl2gGuestNetworkTable 1 }
           
 	Wl2gGuestNetworkEntry ::= SEQUENCE {
		gIndexWl2g			INTEGER,
		gEnableWl2g			INTEGER,
		gSSIDWl2g			OCTET STRING,
		gAuthenticationWl2g	INTEGER,
		gWepEncryptionWl2g	INTEGER,
		gKeyIndexWl2g		INTEGER,
		gPassphraseWl2g		OCTET STRING,
		gWpaEncryptionWl2g	INTEGER,
		gWpaPreSharedKeyWl2g	OCTET STRING,
		gAccessTimeWl2g		INTEGER,
		gAccessTimeHWl2g	INTEGER,
		gAccessTimeMWl2g	INTEGER,
		gAccessIntranetWl2g	INTEGER,
		gEnableMacFilterWl2g INTEGER
    	}
           
	gIndexWl2g		OBJECT-TYPE
				SYNTAX INTEGER ( 1..3 )
				MAX-ACCESS not-accessible
				STATUS current
				DESCRIPTION
					"Guest Network List Index for 2G."
				::= { wl2gGuestNetworkEntry 1 }

	gEnableWl2g		OBJECT-TYPE
				SYNTAX INTEGER { enable(1), disable(2) }
				MAX-ACCESS read-write
				STATUS current
				DESCRIPTION
					"The enable of guest network list for 2G."
				::= { wl2gGuestNetworkEntry 2 }

	gSSIDWl2g		OBJECT-TYPE
				SYNTAX OCTET STRING ( SIZE (1..32) )
				MAX-ACCESS read-write
				STATUS current
				DESCRIPTION
					"The SSID of guest network list for 2G."
				::= { wl2gGuestNetworkEntry 3 }

	gAuthenticationWl2g	OBJECT-TYPE                              
                SYNTAX INTEGER { opensystem(1), sharedkey(2), wpa-personal(3), wpa2-personal(4), wpa-auto-personal(5), wpa-enterprise(6), wpa2-enterprise(7), wpa-auto-enterprise(8), radius-with-8021x(9) }
				MAX-ACCESS read-write
				STATUS current
				DESCRIPTION
					"The authentication method of guest network list of 2G. 
					Open system with wep key, shared key, and radius with 802.1x are 
					only supported when wireless mode is legacy."
				::= { wl2gGuestNetworkEntry 4 }

	gWepEncryptionWl2g	OBJECT-TYPE
				SYNTAX INTEGER { none(1), wep-64bits(2), wep-128bits(3) }
				MAX-ACCESS read-write
				STATUS current
				DESCRIPTION 
					"The wep encryption of guest network list for 2G."
				::= { wl2gGuestNetworkEntry 5 }

	gKeyIndexWl2g		OBJECT-TYPE
				SYNTAX INTEGER { first(1), second(2), third(3), forth(4) }
				MAX-ACCESS read-write                      
                                STATUS current
				DESCRIPTION
					"The key index of guest network list for 2G."
				::= { wl2gGuestNetworkEntry 6 } 

	gPassphraseWl2g		OBJECT-TYPE
                SYNTAX OCTET STRING
                MAX-ACCESS read-write
                STATUS current
				DESCRIPTION
					"The passphrase of guest network list for 2G."
				::= { wl2gGuestNetworkEntry 7 } 

	gWpaEncryptionWl2g	OBJECT-TYPE
				SYNTAX INTEGER { tkip(1), aes(2), tkip-aes(3), none(0) }
				MAX-ACCESS read-write
				STATUS current
				DESCRIPTION
					"The WPA encryption of guest network list for 2G."   
                                ::= { wl2gGuestNetworkEntry 8 }

	gWpaPreSharedKeyWl2g	OBJECT-TYPE
                SYNTAX OCTET STRING
                MAX-ACCESS read-write
                STATUS current
				DESCRIPTION
					"The WPA pre-shared key of guest network list for 2G."
				::= { wl2gGuestNetworkEntry 9 }

	gAccessTimeWl2g		OBJECT-TYPE
				SYNTAX INTEGER { specific-time(1), limitless(2) }
				MAX-ACCESS read-write
				STATUS current
				DESCRIPTION
					"The access time of guest network list for 2G."
				::= { wl2gGuestNetworkEntry 10 }

	gAccessTimeHWl2g	OBJECT-TYPE
				SYNTAX INTEGER ( 0..23 )
				MAX-ACCESS read-write
				STATUS current
				DESCRIPTION
					"The access time (hour) of guest network list for 2G."
				::= { wl2gGuestNetworkEntry 11 }

	gAccessTimeMWl2g	OBJECT-TYPE
				SYNTAX INTEGER ( 0..59 )
				MAX-ACCESS read-write
				STATUS current
				DESCRIPTION
					"The access time (minute) of guest network list for 2G."
				::= { wl2gGuestNetworkEntry 12 }

	gAccessIntranetWl2g	OBJECT-TYPE
				SYNTAX INTEGER { enable(1), disable(2) }
				MAX-ACCESS read-write
				STATUS current
				DESCRIPTION
					"The access intranet of guest network list for 2G."
				::= { wl2gGuestNetworkEntry 13 }    

	gEnableMacFilterWl2g	OBJECT-TYPE
	 			SYNTAX INTEGER { yes(1), no(2) }
				MAX-ACCESS read-write
				STATUS current
				DESCRIPTION
					"Enable MAC filter of guest network of 2G. Note: MAC filter function of primary SSID must be enabled first. "
				::= { wl2gGuestNetworkEntry 14 }
				

	gSSIDWepKeyWl2g		OBJECT IDENTIFIER ::= { guest-network-wl2g 2 }
    
	gWl2gSSID1WepKeyTable	OBJECT-TYPE
				SYNTAX SEQUENCE OF GWepKeyEntry1Wl2g
				MAX-ACCESS not-accessible
				STATUS current
				DESCRIPTION
					"Wep key table of guest network 1 for 2G."
				::= { gSSIDWepKeyWl2g 1 }
      
	gWepKeyEntry1Wl2g	OBJECT-TYPE
				SYNTAX GWepKeyEntry1Wl2g
				MAX-ACCESS not-accessible
				STATUS current
				DESCRIPTION ""
				INDEX {gWepKeyIndex1Wl2g }
				::= { gWl2gSSID1WepKeyTable 1 }

	GWepKeyEntry1Wl2g ::= SEQUENCE {
        	gWepKeyIndex1Wl2g      	INTEGER,
        	gWepKeyValue1Wl2g	OCTET STRING
	}                                    

	gWepKeyIndex1Wl2g	OBJECT-TYPE
				SYNTAX INTEGER ( 1..4 )
				MAX-ACCESS not-accessible
				STATUS current
				DESCRIPTION
					"Wep key index of guest network 1 for 2G."
				::= { gWepKeyEntry1Wl2g 1 }

	gWepKeyValue1Wl2g	OBJECT-TYPE
				SYNTAX OCTET STRING
				MAX-ACCESS read-write
				STATUS current
				DESCRIPTION
					"WEP key value of guest network 1 for 2G."
				::= { gWepKeyEntry1Wl2g 2 }

	gWl2gSSID2WepKeyTable	OBJECT-TYPE
				SYNTAX SEQUENCE OF GWepKeyEntry2Wl2g
				MAX-ACCESS not-accessible
				STATUS current
				DESCRIPTION
					"Wep key table of guest network 2 for 2G."
				::= { gSSIDWepKeyWl2g 2 }
      
	gWepKeyEntry2Wl2g	OBJECT-TYPE
				SYNTAX GWepKeyEntry2Wl2g
				MAX-ACCESS not-accessible
				STATUS current
				DESCRIPTION ""
				INDEX {gWepKeyIndex2Wl2g }
				::= { gWl2gSSID2WepKeyTable 1 }

	GWepKeyEntry2Wl2g ::= SEQUENCE {
        	gWepKeyIndex2Wl2g      	INTEGER,
        	gWepKeyValue2Wl2g	OCTET STRING
	}                                    

	gWepKeyIndex2Wl2g	OBJECT-TYPE
				SYNTAX INTEGER ( 1..4 )
				MAX-ACCESS not-accessible
				STATUS current
				DESCRIPTION
					"Wep key index of guest network 2 for 2G."
				::= { gWepKeyEntry2Wl2g 1 }

	gWepKeyValue2Wl2g	OBJECT-TYPE
				SYNTAX OCTET STRING
				MAX-ACCESS read-write
				STATUS current
				DESCRIPTION
					"WEP key value of guest network 2 for 2G."
				::= { gWepKeyEntry2Wl2g 2 }


	gWl2gSSID3WepKeyTable	OBJECT-TYPE
				SYNTAX SEQUENCE OF GWepKeyEntry3Wl2g
				MAX-ACCESS not-accessible
				STATUS current
				DESCRIPTION
					"Wep key table of guest network 3 for 2G."
				::= { gSSIDWepKeyWl2g 3 }
      
	gWepKeyEntry3Wl2g	OBJECT-TYPE
				SYNTAX GWepKeyEntry3Wl2g
				MAX-ACCESS not-accessible
				STATUS current
				DESCRIPTION ""
				INDEX {gWepKeyIndex3Wl2g }
				::= { gWl2gSSID3WepKeyTable 1 }

	GWepKeyEntry3Wl2g ::= SEQUENCE {
        	gWepKeyIndex3Wl2g      	INTEGER,
        	gWepKeyValue3Wl2g	OCTET STRING
	}                                    

	gWepKeyIndex3Wl2g	OBJECT-TYPE
				SYNTAX INTEGER ( 1..4 )
				MAX-ACCESS not-accessible
				STATUS current
				DESCRIPTION
					"Wep key index of guest network 3 for 2G."
				::= { gWepKeyEntry3Wl2g 1 }

	gWepKeyValue3Wl2g	OBJECT-TYPE
				SYNTAX OCTET STRING
				MAX-ACCESS read-write
				STATUS current
				DESCRIPTION
					"WEP key value of guest network 3 for 2G."
				::= { gWepKeyEntry3Wl2g 2 } 
				
-- ++++++++++++++++++++++++++++++++++++++++++++++++++++++++++++++++++++++
-- *  End of Guest Network Section (2.4G)
-- ++++++++++++++++++++++++++++++++++++++++++++++++++++++++++++++++++++++

-- ++++++++++++++++++++++++++++++++++++++++++++++++++++++++++++++++++++++
-- +  Guest Network Section (5G)
-- ++++++++++++++++++++++++++++++++++++++++++++++++++++++++++++++++++++++

	guest-network-wl5g	OBJECT IDENTIFIER ::= { guestNetwork 2 }
                                                                                                               
	wl5gGuestNetworkTable	OBJECT-TYPE
                                SYNTAX SEQUENCE OF Wl5gGuestNetworkEntry
                                MAX-ACCESS not-accessible
                                STATUS current
                                DESCRIPTION
                                	"Guest network list for 5G."
                                ::= { guest-network-wl5g 1 }
                                
	wl5gGuestNetworkEntry	OBJECT-TYPE
				SYNTAX Wl5gGuestNetworkEntry
				MAX-ACCESS not-accessible
				STATUS current
				DESCRIPTION ""
				INDEX { gIndexWl5g }
				::= { wl5gGuestNetworkTable 1 }
                                
   	Wl5gGuestNetworkEntry ::= SEQUENCE {
		gIndexWl5g			INTEGER,
		gEnableWl5g			INTEGER,
		gSSIDWl5g			OCTET STRING,
		gAuthenticationWl5g	INTEGER,
		gWepEncryptionWl5g	INTEGER,
		gKeyIndexWl5g		INTEGER,
		gPassphraseWl5g		OCTET STRING,
		gWpaEncryptionWl5g	INTEGER,
		gWpaPreSharedKeyWl5g	OCTET STRING,
		gAccessTimeWl5g		INTEGER,
		gAccessTimeHWl5g	INTEGER,
		gAccessTimeMWl5g	INTEGER,
		gAccessIntranetWl5g	INTEGER,
		gEnableMacFilterWl5g INTEGER		
    	}

    
	gIndexWl5g	OBJECT-TYPE
				SYNTAX INTEGER ( 1..3 )
				MAX-ACCESS not-accessible
				STATUS current
				DESCRIPTION
					"Guest Network List Index for 5G."
				::= { wl5gGuestNetworkEntry 1 }

	gEnableWl5g	OBJECT-TYPE
				SYNTAX INTEGER { enable(1), disable(2) }
				MAX-ACCESS read-write
				STATUS current
				DESCRIPTION
					"The enable of guest network list for 5G."
				::= { wl5gGuestNetworkEntry 2 }

	gSSIDWl5g	OBJECT-TYPE
				SYNTAX OCTET STRING ( SIZE (1..32) )
				MAX-ACCESS read-write
				STATUS current
				DESCRIPTION
					"The SSID of guest network list for 5G."
				::= { wl5gGuestNetworkEntry 3 }

	gAuthenticationWl5g	OBJECT-TYPE                              
                SYNTAX INTEGER { opensystem(1), sharedkey(2), wpa-personal(3), wpa2-personal(4), wpa-auto-personal(5), wpa-enterprise(6), wpa2-enterprise(7), wpa-auto-enterprise(8), radius-with-8021x(9) }
				MAX-ACCESS read-write
				STATUS current
				DESCRIPTION
					"The authentication method of guest network list of 5G.
					Open system with wep key, shared key, and radius with 802.1x are 
					only supported when wireless mode is legacy."
				::= { wl5gGuestNetworkEntry 4 }

	gWepEncryptionWl5g	OBJECT-TYPE
				SYNTAX INTEGER { none(1), wep-64bits(2), wep-128bits(3) }
				MAX-ACCESS read-write
				STATUS current
				DESCRIPTION 
					"The wep encryption of guest network list for 5G."
				::= { wl5gGuestNetworkEntry 5 }

	gKeyIndexWl5g	OBJECT-TYPE
				SYNTAX INTEGER { first(1), second(2), third(3), forth(4) }
				MAX-ACCESS read-write                      
                STATUS current
				DESCRIPTION
					"The key index of guest network list for 5G."
					::= { wl5gGuestNetworkEntry 6 } 

	gPassphraseWl5g		OBJECT-TYPE
                SYNTAX OCTET STRING
                MAX-ACCESS read-write
                STATUS current
				DESCRIPTION
					"The passphrase of guest network list for 5G."
				::= { wl5gGuestNetworkEntry 7 } 

	gWpaEncryptionWl5g	OBJECT-TYPE
				SYNTAX INTEGER { tkip(1), aes(2), tkip-aes(3), none(0) }
				MAX-ACCESS read-write
				STATUS current
				DESCRIPTION
					"The WPA encryption of guest network list for 5G."   
                ::= { wl5gGuestNetworkEntry 8 }

	gWpaPreSharedKeyWl5g	OBJECT-TYPE
                SYNTAX OCTET STRING
                MAX-ACCESS read-write
                STATUS current
				DESCRIPTION
					"The WPA pre-shared key of guest network list for 5G."
				::= { wl5gGuestNetworkEntry 9 }

	gAccessTimeWl5g		OBJECT-TYPE
				SYNTAX INTEGER { specific-time(1), limitless(2) }
				MAX-ACCESS read-write
				STATUS current
				DESCRIPTION
					"The access time of guest network list for 5G."
				::= { wl5gGuestNetworkEntry 10 }

	gAccessTimeHWl5g	OBJECT-TYPE
				SYNTAX INTEGER ( 0..23 )
				MAX-ACCESS read-write
				STATUS current
				DESCRIPTION
					"The access time (hour) of guest network list for 5G."
				::= { wl5gGuestNetworkEntry 11 }

	gAccessTimeMWl5g	OBJECT-TYPE
				SYNTAX INTEGER ( 0..59 )
				MAX-ACCESS read-write
				STATUS current
				DESCRIPTION
					"The access time (minute) of guest network list for 5G."
				::= { wl5gGuestNetworkEntry 12 }

	gAccessIntranetWl5g	OBJECT-TYPE
				SYNTAX INTEGER { enable(1), disable(2) }
				MAX-ACCESS read-write
				STATUS current
				DESCRIPTION
					"The access intranet of guest network list for 5G."
				::= { wl5gGuestNetworkEntry 13 } 

	gEnableMacFilterWl5g	OBJECT-TYPE
	 			SYNTAX INTEGER { yes(1), no(2) }
				MAX-ACCESS read-write
				STATUS current
				DESCRIPTION
					"Enable MAC filter of guest network of 5G. Note: MAC filter function of primary SSID must be enabled first. "
				::= { wl5gGuestNetworkEntry 14 }				

	gSSIDWepKeyWl5g		OBJECT IDENTIFIER ::= { guest-network-wl5g 2 }
    
	gWl5gSSID1WepKeyTable	OBJECT-TYPE
				SYNTAX SEQUENCE OF GWepKeyEntry1Wl5g
				MAX-ACCESS not-accessible
				STATUS current
				DESCRIPTION
					"Wep key table of guest network 1 for 5G."
				::= { gSSIDWepKeyWl5g 1 }
      
	gWepKeyEntry1Wl5g	OBJECT-TYPE
				SYNTAX GWepKeyEntry1Wl5g
				MAX-ACCESS not-accessible
				STATUS current
				DESCRIPTION ""
				INDEX {gWepKeyIndex1Wl5g }
				::= { gWl5gSSID1WepKeyTable 1 }

	GWepKeyEntry1Wl5g ::= SEQUENCE {
        	gWepKeyIndex1Wl5g      	INTEGER,
        	gWepKeyValue1Wl5g	OCTET STRING
	}                                    

	gWepKeyIndex1Wl5g	OBJECT-TYPE
				SYNTAX INTEGER ( 1..4 )
				MAX-ACCESS not-accessible
				STATUS current
				DESCRIPTION
					"Wep key index of guest network 1 for 5G."
				::= { gWepKeyEntry1Wl5g 1 }

	gWepKeyValue1Wl5g	OBJECT-TYPE
				SYNTAX OCTET STRING
				MAX-ACCESS read-write
				STATUS current
				DESCRIPTION
					"WEP key value of guest network 1 for 5G."
				::= { gWepKeyEntry1Wl5g 2 }

	gWl5gSSID2WepKeyTable	OBJECT-TYPE
				SYNTAX SEQUENCE OF GWl5gSSID2WepKeyEntry
				MAX-ACCESS not-accessible
				STATUS current
				DESCRIPTION
					"Wep key table of guest network 2 for 5G."
				::= { gSSIDWepKeyWl5g 2 }
      
	gWl5gSSID2WepKeyEntry	OBJECT-TYPE
				SYNTAX GWl5gSSID2WepKeyEntry
				MAX-ACCESS not-accessible
				STATUS current
				DESCRIPTION ""
				INDEX {gWepKeyIndex2Wl5g }
				::= { gWl5gSSID2WepKeyTable 1 }

	GWl5gSSID2WepKeyEntry ::= SEQUENCE {
        	gWepKeyIndex2Wl5g      	INTEGER,
        	gWepKeyValue2Wl5g	OCTET STRING
	}                                    

	gWepKeyIndex2Wl5g	OBJECT-TYPE
				SYNTAX INTEGER ( 1..4 )
				MAX-ACCESS not-accessible
				STATUS current
				DESCRIPTION
					"Wep key index of guest network 2 for 5G."
				::= { gWl5gSSID2WepKeyEntry 1 }

	gWepKeyValue2Wl5g	OBJECT-TYPE
				SYNTAX OCTET STRING
				MAX-ACCESS read-write
				STATUS current
				DESCRIPTION
					"WEP key value of guest network 2 for 5G."
				::= { gWl5gSSID2WepKeyEntry 2 }


	gWl5gSSID3WepKeyTable	OBJECT-TYPE
				SYNTAX SEQUENCE OF GWepKeyEntry3Wl5g
				MAX-ACCESS not-accessible
				STATUS current
				DESCRIPTION
					"Wep key table of guest network 3 for 5G."
				::= { gSSIDWepKeyWl5g 3 }
      
	gWl5gSSID3WepKeyEntry	OBJECT-TYPE
				SYNTAX GWepKeyEntry3Wl5g
				MAX-ACCESS not-accessible
				STATUS current
				DESCRIPTION ""
				INDEX {gWepKeyIndex3Wl5g }
				::= { gWl5gSSID3WepKeyTable 1 }

	GWepKeyEntry3Wl5g ::= SEQUENCE {
        	gWepKeyIndex3Wl5g      	INTEGER,
        	gWepKeyValue3Wl5g	OCTET STRING
	}                                    

	gWepKeyIndex3Wl5g	OBJECT-TYPE
				SYNTAX INTEGER ( 1..4 )
				MAX-ACCESS not-accessible
				STATUS current
				DESCRIPTION
					"Wep key index of guest network 3 for 5G."
				::= { gWl5gSSID3WepKeyEntry 1 }

	gWepKeyValue3Wl5g	OBJECT-TYPE
				SYNTAX OCTET STRING
				MAX-ACCESS read-write
				STATUS current
				DESCRIPTION
					"WEP key value of guest network 3 for 5G."
				::= { gWl5gSSID3WepKeyEntry 2 }

-- ++++++++++++++++++++++++++++++++++++++++++++++++++++++++++++++++++++++
-- *  End of Guest Network Section (5G)
-- ++++++++++++++++++++++++++++++++++++++++++++++++++++++++++++++++++++++

-- **********************************************************************
-- *  End of Guest Network Section 
-- **********************************************************************

-- ======================================================================
-- * End of Guest Network Section
-- ======================================================================





-- ======================================================================
-- * Traffic Manager Section
-- ======================================================================

-- **********************************************************************
-- *  QoS Section 
-- **********************************************************************

-- ++++++++++++++++++++++++++++++++++++++++++++++++++++++++++++++++++++++
-- *  Automatic Mode Section 
-- ++++++++++++++++++++++++++++++++++++++++++++++++++++++++++++++++++++++

	automatic-mode		OBJECT IDENTIFIER ::= { trafficManager 1 }

	enableQoS			OBJECT-TYPE
                        SYNTAX INTEGER { on(1), off(2) }
						MAX-ACCESS read-write
						STATUS current                                                        
                        DESCRIPTION ""
						::= { automatic-mode 1 }

	uploadBandwidth		OBJECT-TYPE
                        SYNTAX INTEGER
						MAX-ACCESS read-write
						STATUS current                                                        
                        DESCRIPTION
						"If the measured uplink speed is incorrect, you can assign it manually here."
						::= { automatic-mode 2 }

	downloadBandwidth	OBJECT-TYPE
                        SYNTAX INTEGER
						MAX-ACCESS read-write
						STATUS current                                                        
                        DESCRIPTION
							"If the measured downlink speed is incorrect, you can assign it manually here."
						::= { automatic-mode 3 }

-- ++++++++++++++++++++++++++++++++++++++++++++++++++++++++++++++++++++++
-- *  End of Automatic Mode Section 
-- ++++++++++++++++++++++++++++++++++++++++++++++++++++++++++++++++++++++

-- ++++++++++++++++++++++++++++++++++++++++++++++++++++++++++++++++++++++
-- *  User Defined QoS rules Section
-- ++++++++++++++++++++++++++++++++++++++++++++++++++++++++++++++++++++++

	user-defined-qos-rules	OBJECT IDENTIFIER ::= { trafficManager 2 }

	userSpecifyRuleTable	OBJECT-TYPE
				SYNTAX SEQUENCE OF UserSpecifyRuleEntry
				MAX-ACCESS not-accessible
				STATUS current
				DESCRIPTION
					"User specify rule list."
				::= { user-defined-qos-rules 1 }

	userSpecifyRuleEntry	OBJECT-TYPE
				SYNTAX UserSpecifyRuleEntry
				MAX-ACCESS not-accessible
				STATUS current
				DESCRIPTION ""
				INDEX { userSpecifyRuleIndex }
				::= { userSpecifyRuleTable 1 }

 	UserSpecifyRuleEntry ::= SEQUENCE {
    	    	userSpecifyRuleIndex			INTEGER,
        		userSpecifyRuleServiceName		OCTET STRING,
				userSpecifyRuleSrcIPorMAC		OCTET STRING,
				userSpecifyRuleDestPort			OCTET STRING,
				userSpecifyRuleProtocol			INTEGER,
				userSpecifyRuleMinTransferred	OCTET STRING,
				userSpecifyRuleMaxTransferred	OCTET STRING,
				userSpecifyRulePriority			INTEGER,
        		userSpecifyRuleDelEntry			INTEGER
    	}                           
    
	userSpecifyRuleIndex	OBJECT-TYPE
				SYNTAX INTEGER  (1..32)
				MAX-ACCESS not-accessible
				STATUS current
				DESCRIPTION 
					"User Specify Rule Index."
				::= { userSpecifyRuleEntry 1 }

	userSpecifyRuleServiceName	OBJECT-TYPE
				SYNTAX OCTET STRING
				MAX-ACCESS read-write
				STATUS current
				DESCRIPTION
					"Service name of user specify rule list."
				::= { userSpecifyRuleEntry 2 }

	userSpecifyRuleSrcIPorMAC	OBJECT-TYPE
				SYNTAX OCTET STRING
				MAX-ACCESS read-write
				STATUS current
				DESCRIPTION
					"For source or destination IP address, you can : 
					(a) enter a specific IP address, such as '192.168.122.1'; 
					(b) enter IP addresses within one subnet or within the same IP pool, such as '192.168.123.*', or '192.168.*.*'; or 
					(c) enter all IP addresses as '*.*.*.*\'."
				::= { userSpecifyRuleEntry 3 }

	userSpecifyRuleDestPort	OBJECT-TYPE
				SYNTAX OCTET STRING
				MAX-ACCESS read-write
				STATUS current
				DESCRIPTION
					"Destination port of user specify rule list."
				::= { userSpecifyRuleEntry 4 }

	userSpecifyRuleProtocol	OBJECT-TYPE
				SYNTAX INTEGER { tcp(1), udp(2), tcp-or-udp(3), any(4) }
				MAX-ACCESS read-write
				STATUS current
				DESCRIPTION
					"Protocol of user specify rule list."
				::= { userSpecifyRuleEntry 5 }

	userSpecifyRuleMinTransferred	OBJECT-TYPE
				SYNTAX OCTET STRING
				MAX-ACCESS read-write
				STATUS current
				DESCRIPTION
					"Set the network traffic limit (in KB) for a specific service to generate 
					specific priorities for the service assigned to a specific port. 
					For example, if two network clients, PC 1 and PC 2, are both accessing the 
					Internet (set at port 80), but PC 1 exceeded the network traffic limit due 
					to some downloading tasks, PC 1 will be given a lower priority. 
					The Transferred column refers to the upstream and downstream traffic 
					(outgoing and incoming network traffic) for one session. 
					If you do not want to set the traffic limit, you can leave it blank."
				::= { userSpecifyRuleEntry 6 }
	
	userSpecifyRuleMaxTransferred	OBJECT-TYPE
				SYNTAX OCTET STRING
				MAX-ACCESS read-write
				STATUS current
				DESCRIPTION
					"Set the network traffic limit (in KB) for a specific service to generate 
					specific priorities for the service assigned to a specific port. 
					For example, if two network clients, PC 1 and PC 2, are both accessing the 
					Internet (set at port 80), but PC 1 exceeded the network traffic limit due 
					to some downloading tasks, PC 1 will be given a lower priority. 
					The Transferred column refers to the upstream and downstream traffic 
					(outgoing and incoming network traffic) for one session. 
					If you do not want to set the traffic limit, you can leave it blank."
				::= { userSpecifyRuleEntry 7 }

	userSpecifyRulePriority	OBJECT-TYPE
				SYNTAX INTEGER { highest(1), high(2), medium(3), low(4), lowest(5) }
				MAX-ACCESS read-write
				STATUS current
				DESCRIPTION
					"Priority of user specify rule list."
				::= { userSpecifyRuleEntry 8 }

	userSpecifyRuleDelEntry	OBJECT-TYPE
				SYNTAX INTEGER { yes(1), no(2) }
				MAX-ACCESS read-write
				STATUS current
				DESCRIPTION
					"Delete the user specify rule enntry."
				::= { userSpecifyRuleEntry 9 }

-- ++++++++++++++++++++++++++++++++++++++++++++++++++++++++++++++++++++++
-- *  End of User Defined QoS rules Section
-- ++++++++++++++++++++++++++++++++++++++++++++++++++++++++++++++++++++++

-- ++++++++++++++++++++++++++++++++++++++++++++++++++++++++++++++++++++++
-- *  User Defined Priority Section 
-- ++++++++++++++++++++++++++++++++++++++++++++++++++++++++++++++++++++++

	user-defined-priority	OBJECT IDENTIFIER ::= { trafficManager 3 }

	upload-bandwidth		OBJECT IDENTIFIER ::= { user-defined-priority 1 }
	
	upHighestMinReserveBd	OBJECT-TYPE
						SYNTAX INTEGER ( 0..100 )
                        MAX-ACCESS read-write
                        STATUS current
                        DESCRIPTION
                        "Minimum reserved bandwidth of highest upload priority."
                        ::= { upload-bandwidth 1 }

	upHighestMaxBd		OBJECT-TYPE
                        SYNTAX INTEGER ( 0..100 )
                        MAX-ACCESS read-write
                        STATUS current
                        DESCRIPTION
                        	"Maximum bandwidth limit of highest upload priority."
                        ::= { upload-bandwidth 2 }

	upHighMinReserveBd	OBJECT-TYPE
                        SYNTAX INTEGER ( 0..100 )
                        MAX-ACCESS read-write
                        STATUS current
                        DESCRIPTION
                        	"Minimum reserved bandwidth of high upload priority."
                        ::= { upload-bandwidth 3 }

	upHighMaxBd			OBJECT-TYPE
                        SYNTAX INTEGER ( 0..100 )
                        MAX-ACCESS read-write
                        STATUS current
                        DESCRIPTION
                        	"Maximum bandwidth limit of high upload priority."
                        ::= { upload-bandwidth 4 }

	upMediumMinReserveBd	OBJECT-TYPE
                        SYNTAX INTEGER ( 0..100 )
                        MAX-ACCESS read-write
                        STATUS current
                        DESCRIPTION
                          	"Minimum reserved bandwidth of medium upload priority."
                        ::= { upload-bandwidth 5 }

	upMediumMaxBd		OBJECT-TYPE
                        SYNTAX INTEGER ( 0..100 )
                        MAX-ACCESS read-write
                        STATUS current
                        DESCRIPTION
                        	"Maximum bandwidth limit of medium upload priority."
                        ::= { upload-bandwidth 6 }

	upLowMinReserveBd	OBJECT-TYPE
                        SYNTAX INTEGER ( 0..100 )
                        MAX-ACCESS read-write
                        STATUS current
                        DESCRIPTION
                           	"Minimum reserved bandwidth of low upload priority."
                        ::= { upload-bandwidth 7 }

	upLowMaxBd			OBJECT-TYPE
                        SYNTAX INTEGER ( 0..100 )
                        MAX-ACCESS read-write
                        STATUS current
                        DESCRIPTION
                        	"Maximum bandwidth limit of low upload priority."
                        ::= { upload-bandwidth 8 }

	upLowestMinReserveBd	OBJECT-TYPE
                        SYNTAX INTEGER ( 0..100 )
                        MAX-ACCESS read-write
                        STATUS current
                        DESCRIPTION
                          	"Minimum reserved bandwidth of lowest upload priority."
                        ::= { upload-bandwidth 9 }

	upLowestMaxBd		OBJECT-TYPE
                        SYNTAX INTEGER ( 0..100 )
                        MAX-ACCESS read-write
                        STATUS current
                        DESCRIPTION
                          	"Maximum bandwidth limit of lowest upload priority."
                        ::= { upload-bandwidth 10 }

	download-bandwidth	OBJECT IDENTIFIER ::= { user-defined-priority 2 }

	downHighestMaxBd	OBJECT-TYPE
                        SYNTAX INTEGER ( 0..100 )
                        MAX-ACCESS read-write
                        STATUS current
                        DESCRIPTION
                        	"Maximum bandwidth limit of highest download priority."
                        ::= { download-bandwidth 1 }

	downHighMaxBd		OBJECT-TYPE
                        SYNTAX INTEGER ( 0..100 )
                        MAX-ACCESS read-write
                        STATUS current
                        DESCRIPTION
                           	"Maximum bandwidth limit of high download priority."
                        ::= { download-bandwidth 2 }

	downMediumMaxBd		OBJECT-TYPE
                        SYNTAX INTEGER ( 0..100 )
                        MAX-ACCESS read-write
                        STATUS current
                        DESCRIPTION
                           	"Maximum bandwidth limit of medium download priority."
                        ::= { download-bandwidth 3 }

	downLowMaxBd		OBJECT-TYPE
                        SYNTAX INTEGER ( 0..100 )
                        MAX-ACCESS read-write
                        STATUS current
                        DESCRIPTION
                        	"Maximum bandwidth limit of low download priority."
                        ::= { download-bandwidth 4 }

	downLowestMaxBd		OBJECT-TYPE
                       	SYNTAX INTEGER ( 0..100 )
                        MAX-ACCESS read-write
                        STATUS current
                        DESCRIPTION
                        	"Maximum bandwidth limit of lowest download priority."
                        ::= { download-bandwidth 5 }

	highestPriorityPacket	OBJECT-TYPE
						SYNTAX BITS { ack(0), syn(1), fin(2), rst(3), icmp(4) }
						MAX-ACCESS read-write
						STATUS current
						DESCRIPTION ""
						::= { user-defined-priority 3 }

-- ++++++++++++++++++++++++++++++++++++++++++++++++++++++++++++++++++++++
-- *  End of User Defined Priority Section
-- ++++++++++++++++++++++++++++++++++++++++++++++++++++++++++++++++++++++

-- **********************************************************************
-- *  End of QoS Section 
-- **********************************************************************

-- ======================================================================
-- * End of Traffic Manager Section
-- ======================================================================

 
 
 
 
-- ======================================================================
-- * Parental Control Section
-- ======================================================================
	pControlEnable	OBJECT-TYPE
				SYNTAX INTEGER { on(1), off(2) }
				MAX-ACCESS read-write
				STATUS current
				DESCRIPTION
					"Enable parental control."
				::= { parentalControl  1 }     
				
	pControlScanClients		OBJECT-TYPE
				SYNTAX INTEGER { scan(1), nothing(2) }
				MAX-ACCESS read-write
				STATUS current
				DESCRIPTION ""
				::= { parentalControl  2 }

	pControlScanTable		OBJECT-TYPE
				SYNTAX SEQUENCE OF PControlScanEntry
				MAX-ACCESS not-accessible
				STATUS current
				DESCRIPTION ""
				::= { parentalControl 3 }

	pControlScanEntry		OBJECT-TYPE
				SYNTAX PControlScanEntry
				MAX-ACCESS not-accessible
				STATUS current
				DESCRIPTION ""
				INDEX { pControlScanIndex }
				::= { pControlScanTable 1 }

 	PControlScanEntry ::= SEQUENCE {
        	pControlScanIndex    	INTEGER,
        	pControlScanIPAddr	    IpAddress,
        	pControlScanClientName	OCTET STRING,  
        	pControlScanClientMac   MacAddress    	
    	}

	pControlScanIndex		OBJECT-TYPE
				SYNTAX INTEGER ( 1..32 )
				MAX-ACCESS not-accessible
				STATUS current
				DESCRIPTION
					"Client entry index."
				::= { pControlScanEntry 1 }

	pControlScanIPAddr		OBJECT-TYPE
				SYNTAX IpAddress
				MAX-ACCESS read-only
				STATUS current
				DESCRIPTION
					"MAC address of the client."
				::= { pControlScanEntry 2 }

	pControlScanClientName	OBJECT-TYPE
				SYNTAX OCTET STRING
				MAX-ACCESS read-only
				STATUS current
				DESCRIPTION
					"Name of the client."
				::= { pControlScanEntry 3 }     
				
	pControlScanClientMac	OBJECT-TYPE
				SYNTAX MacAddress
				MAX-ACCESS read-only
				STATUS current
				DESCRIPTION
					"MAC address of the client."
				::= { pControlScanEntry 4 }				
	
  	pControlClientTable	OBJECT-TYPE
				SYNTAX SEQUENCE OF PControlClientEntry
				MAX-ACCESS not-accessible
				STATUS current
				DESCRIPTION
					"Parental control client list."
				::= { parentalControl  4 }
      
	pControlClientEntry	OBJECT-TYPE
				SYNTAX PControlClientEntry
				MAX-ACCESS not-accessible
				STATUS current
				DESCRIPTION ""
				INDEX {pControlClientIndex }
				::= { pControlClientTable 1 }

	PControlClientEntry ::= SEQUENCE {
        	pControlClientIndex      	INTEGER, 
        	pControlEntryEnable				INTEGER,
        	pControlClientName			OCTET STRING,
        	pControlClientMac			MacAddress, 
        	pControlSunAllowTime		OCTET STRING,
        	pControlMonAllowTime		OCTET STRING,
        	pControlTueAllowTime		OCTET STRING,
        	pControlWedAllowTime		OCTET STRING,
        	pControlThuAllowTime		OCTET STRING,
        	pControlFriAllowTime		OCTET STRING,
        	pControlSatAllowTime		OCTET STRING,
        	pControlClientDelEntry		INTEGER
	}                                    

	pControlClientIndex	OBJECT-TYPE
				SYNTAX INTEGER ( 1..16 )
				MAX-ACCESS not-accessible
				STATUS current
				DESCRIPTION
					"Parental control client list index."
				::= { pControlClientEntry 1 }
    
	pControlEntryEnable	OBJECT-TYPE
				SYNTAX INTEGER { enable(1), disable(0) }
				MAX-ACCESS read-write
				STATUS current
				DESCRIPTION
					"Enable the entry."  
				::= { pControlClientEntry 2 }					
    
	pControlClientName	OBJECT-TYPE
				SYNTAX OCTET STRING
				MAX-ACCESS read-write
				STATUS current
				DESCRIPTION
					"Name of parental control client."
				::= { pControlClientEntry 3 }

   	pControlClientMac	OBJECT-TYPE
				SYNTAX MacAddress
				MAX-ACCESS read-write
				STATUS current
				DESCRIPTION
					"Mac address of parental control client."
				::= { pControlClientEntry 4 }
 
  	pControlSunAllowTime	OBJECT-TYPE
				SYNTAX OCTET STRING
				MAX-ACCESS read-write
				STATUS current
				DESCRIPTION
					"Time on Sunday at which clients are allowed to access internet.
					String format: If client can access internet from 1 o'clock to 3 
					o'clock, from 14 o'clock to 15 o'clock, and form 19 o'clock to 23 
					o'clock, please set '00-03,14-15,19-23'. '00-24' means all day."
				::= { pControlClientEntry 5 }
                                                      
	pControlMonAllowTime	OBJECT-TYPE
				SYNTAX OCTET STRING
				MAX-ACCESS read-write
				STATUS current
				DESCRIPTION
					"Time on Monday at which clients are allowed to access internet.
					String format: If client can access internet from 1 o'clock to 3 
					o'clock, from 14 o'clock to 15 o'clock, and form 19 o'clock to 23 
					o'clock, please set '00-03,14-15,19-23'. '00-24' means all day."
				::= { pControlClientEntry 6 }       
				
	pControlTueAllowTime	OBJECT-TYPE
				SYNTAX OCTET STRING
				MAX-ACCESS read-write
				STATUS current
				DESCRIPTION
					"Time on Tuesday at which clients are allowed to access internet.
					String format: If client can access internet from 1 o'clock to 3 
					o'clock, from 14 o'clock to 15 o'clock, and form 19 o'clock to 23 
					o'clock, please set '00-03,14-15,19-23'. '00-24' means all day."
				::= { pControlClientEntry 7 }
				
 	pControlWedAllowTime	OBJECT-TYPE
				SYNTAX OCTET STRING
				MAX-ACCESS read-write
				STATUS current
				DESCRIPTION
					"Time on Wednesday at which clients are allowed to access internet.
					String format: If client can access internet from 1 o'clock to 3 
					o'clock, from 14 o'clock to 15 o'clock, and form 19 o'clock to 23 
					o'clock, please set '00-03,14-15,19-23'. '00-24' means all day."
				::= { pControlClientEntry 8 }

	pControlThuAllowTime	OBJECT-TYPE
				SYNTAX OCTET STRING
				MAX-ACCESS read-write
				STATUS current
				DESCRIPTION
					"Time on Thursday at which clients are allowed to access internet.
					String format: If client can access internet from 1 o'clock to 3 
					o'clock, from 14 o'clock to 15 o'clock, and form 19 o'clock to 23 
					o'clock, please set '00-03,14-15,19-23'. '00-24' means all day."
				::= { pControlClientEntry 9 }   
				  
	pControlFriAllowTime	OBJECT-TYPE
				SYNTAX OCTET STRING
				MAX-ACCESS read-write
				STATUS current
				DESCRIPTION
					"Time on Friday at which clients are allowed to access internet.
					String format: If client can access internet from 1 o'clock to 3 
					o'clock, from 14 o'clock to 15 o'clock, and form 19 o'clock to 23 
					o'clock, please set '00-03,14-15,19-23'. '00-24' means all day."
				::= { pControlClientEntry 10 }

	pControlSatAllowTime	OBJECT-TYPE
				SYNTAX OCTET STRING
				MAX-ACCESS read-write
				STATUS current
				DESCRIPTION
					"Time on Saturday at which clients are allowed to access internet.
					String format: If client can access internet from 1 o'clock to 3 
					o'clock, from 14 o'clock to 15 o'clock, and form 19 o'clock to 23 
					o'clock, please set '00-03,14-15,19-23'. '00-24' means all day."
				::= { pControlClientEntry 11 }				
                                                     
 	pControlClientDelEntry	OBJECT-TYPE
				SYNTAX INTEGER { yes(1), no(2) }
				MAX-ACCESS read-write
				STATUS current
				DESCRIPTION
					"Delete the entry."
				::= { pControlClientEntry 12 }
 
-- ======================================================================
-- * End of Parental Control Section
-- ======================================================================


 
 
-- ======================================================================
-- * Quick Internet Setup Section
-- ======================================================================
-- **********************************************************************
-- *  qRouterMode Setting Section
-- **********************************************************************

	qRouterMode			OBJECT IDENTIFIER ::= { quickInternetSetup 1 } 

-- ++++++++++++++++++++++++++++++++++++++++++++++++++++++++++++++++++++++
-- *  qRouterMode - Internet Setup Section
-- ++++++++++++++++++++++++++++++++++++++++++++++++++++++++++++++++++++++	
	qRInternetSetup		OBJECT IDENTIFIER ::= { qRouterMode 1 }      
	
	qRConnectionType	OBJECT-TYPE
				SYNTAX INTEGER { automatic-ip(1), pppoe(2), static-ip(3), pptp(4), l2tp(5) }
				MAX-ACCESS read-write
				STATUS current
				DESCRIPTION ""
				::= { qRInternetSetup 1 }
   
---------------------------------------------------------------------------
-- *  qRouterMode - Automatic IP Setting Section
---------------------------------------------------------------------------
   
	qRAutomaticIP	OBJECT IDENTIFIER ::= { qRInternetSetup 2 }    

	qRAHostName	OBJECT-TYPE
                SYNTAX OCTET STRING ( SIZE (1..32) )
                MAX-ACCESS read-write
                STATUS current
                DESCRIPTION
					"This field allows you to provide a host name for RT-AC66U. It is usually requested by your ISP."
                ::= { qRAutomaticIP 1 }

	qRAMacAddress	OBJECT-TYPE
				SYNTAX MacAddress
				MAX-ACCESS read-write
				STATUS current
				DESCRIPTION
					"MAC (Media Access Control) address is a unique identifier that identifies your computer or 
					device in the network. ISPs monitor the MAC addresses of devices that connect to their services, 
					and would disallow Internet connection for new MAC addresses. To fix this issue, you can do 
					either of the following: *Contact your ISP and request to update the MAC address associated 
					with your ISP subscription. *Clone or change the MAC address of the new device to match the 
					MAC address of the original device. (This is optional.)"
				::= { qRAutomaticIP 2 }

	qRAConnectToDnsServerAutomatically	OBJECT-TYPE
				SYNTAX INTEGER { yes(1), no(2) }
				MAX-ACCESS read-write
				STATUS current
				DESCRIPTION ""
                ::= { qRAutomaticIP 3 }

	qRADnsServer1	OBJECT-TYPE
				SYNTAX OCTET STRING ( SIZE (0..15) )
				MAX-ACCESS read-write
				STATUS current
				DESCRIPTION ""
				::= { qRAutomaticIP 4 }

	qRADnsServer2	OBJECT-TYPE
				SYNTAX OCTET STRING ( SIZE (0..15) )
				MAX-ACCESS read-write
				STATUS current
				DESCRIPTION ""
				::= { qRAutomaticIP 5 }

---------------------------------------------------------------------------
-- *  End of qRouterMode - Automatic IP Setting Section
---------------------------------------------------------------------------  

---------------------------------------------------------------------------
-- *  qRouterMode - PPPoE Setting Section
---------------------------------------------------------------------------		
	qRPPPoE	OBJECT IDENTIFIER ::= { qRInternetSetup 3 } 
	  
	qRPPPoEUserName	OBJECT-TYPE
                SYNTAX OCTET STRING ( SIZE (1..64) )
                MAX-ACCESS read-write
                STATUS current
                DESCRIPTION
					"If you subscribe to PPPoE, PPTP or L2TP connection type, your ISP would give you a card or 
					document that contains the account name and password on it. The account name and password that 
					your ISP provided are used to connect to the Internet."
                ::= { qRPPPoE 1 }

	qRPPPoEPassword	OBJECT-TYPE
                SYNTAX OCTET STRING ( SIZE (1..64) )
                MAX-ACCESS read-write
                STATUS current
                DESCRIPTION
					"If you subscribe to PPPoE, PPTP or L2TP connection type, your ISP would give you a card or 
					document that contains the account name and password on it. The account name and password that 
					your ISP provided are used to connect to the Internet."
                ::= { qRPPPoE 2 }
---------------------------------------------------------------------------
-- *  End of qRouterMode - PPPoE Setting Section
--------------------------------------------------------------------------- 

---------------------------------------------------------------------------
-- *  qRouterMode - Static IP Setting Section
---------------------------------------------------------------------------	    
	qRStaticIP	OBJECT IDENTIFIER ::= { qRInternetSetup 4 }  
		    
	qRIPAddress	OBJECT-TYPE
				SYNTAX IpAddress
				MAX-ACCESS read-write
				STATUS current
				DESCRIPTION
		           "If your WAN connection requires a static IP address, key in the IP address in this field."
                ::= { qRStaticIP 1 }

	qRSubnetMask	OBJECT-TYPE
				SYNTAX IpAddress
				MAX-ACCESS read-write
				STATUS current
				DESCRIPTION
					"If your WAN connection requires a static IP address, key in the subnet mask in this field."
				::= { qRStaticIP 2 }

	qRDefaultGateway	OBJECT-TYPE
				SYNTAX IpAddress
				MAX-ACCESS read-write
				STATUS current
				DESCRIPTION 
					"If your WAN connection requires a static IP address, key in the gateway IP address in this field."
				::= { qRStaticIP 3 }

	qRDnsServer1	OBJECT-TYPE
				SYNTAX OCTET STRING ( SIZE (0..15) )
				MAX-ACCESS read-write
				STATUS current
				DESCRIPTION ""
				::= { qRStaticIP 4 }

	qRDnsServer2	OBJECT-TYPE
				SYNTAX OCTET STRING ( SIZE (0..15) ) 
				MAX-ACCESS read-write
				STATUS current
				DESCRIPTION ""
				::= { qRStaticIP 5 }   
				
	qRMacAddress	OBJECT-TYPE
				SYNTAX MacAddress
				MAX-ACCESS read-write
				STATUS current
				DESCRIPTION
					"MAC (Media Access Control) address is a unique identifier that identifies your computer or 
					device in the network. ISPs monitor the MAC addresses of devices that connect to their services, 
					and would disallow Internet connection for new MAC addresses. To fix this issue, you can do 
					either of the following: *Contact your ISP and request to update the MAC address associated 
					with your ISP subscription. *Clone or change the MAC address of the new device to match the 
					MAC address of the original device. (This is optional.)"   
				::= { qRStaticIP 6 }        
---------------------------------------------------------------------------
-- *  End of qRouterMode - Static IP Setting Section
---------------------------------------------------------------------------

---------------------------------------------------------------------------
-- *  qRouterMode - PPTP and L2TP Setting Section
---------------------------------------------------------------------------				   					
	qRPPTPL2TP	OBJECT IDENTIFIER ::= { qRInternetSetup 5 } 

	qRUserName	OBJECT-TYPE
                SYNTAX OCTET STRING ( SIZE (1..64) )
                MAX-ACCESS read-write
                STATUS current
                DESCRIPTION
					"If you subscribe to PPPoE, PPTP or L2TP connection type, your ISP would give you a card or 
					document that contains the account name and password on it. The account name and password that 
					your ISP provided are used to connect to the Internet."
                ::= { qRPPTPL2TP 1 }

	qRPassword	OBJECT-TYPE
                SYNTAX OCTET STRING ( SIZE (1..64) )
                MAX-ACCESS read-write
                STATUS current
                DESCRIPTION
					"If you subscribe to PPPoE, PPTP or L2TP connection type, your ISP would give you a card or 
					document that contains the account name and password on it. The account name and password that 
					your ISP provided are used to connect to the Internet."
                ::= { qRPPTPL2TP 2 }

	qRPIPAddress	OBJECT-TYPE
				SYNTAX IpAddress
				MAX-ACCESS read-write
				STATUS current
				DESCRIPTION
		           "If your WAN connection requires a static IP address, key in the IP address in this field."
                ::= { qRPPTPL2TP 3 }

	qRPSubnetMask	OBJECT-TYPE
				SYNTAX IpAddress
				MAX-ACCESS read-write
				STATUS current
				DESCRIPTION
					"If your WAN connection requires a static IP address, key in the subnet mask in this field."
				::= { qRPPTPL2TP 4 }

	qRPDefaultGateway	OBJECT-TYPE
				SYNTAX IpAddress
				MAX-ACCESS read-write
				STATUS current
				DESCRIPTION 
					"If your WAN connection requires a static IP address, key in the gateway IP address in this field."
				::= { qRPPTPL2TP 5 }
	 
	qRPConnectToDnsServerAutomatically	OBJECT-TYPE
				SYNTAX INTEGER { yes(1), no(2) }
				MAX-ACCESS read-write
				STATUS current
				DESCRIPTION ""
                ::= { qRPPTPL2TP 6 }

	qRPDnsServer1	OBJECT-TYPE
				SYNTAX OCTET STRING ( SIZE (0..15) ) 
				MAX-ACCESS read-write
				STATUS current
				DESCRIPTION ""
				::= { qRPPTPL2TP 7 }

	qRPDnsServer2	OBJECT-TYPE
				SYNTAX OCTET STRING ( SIZE (0..15) ) 
				MAX-ACCESS read-write
				STATUS current
				DESCRIPTION ""
				::= { qRPPTPL2TP 8 }       
				
	qRPvpnServer	OBJECT-TYPE
                SYNTAX OCTET STRING ( SIZE (1..256) )
                MAX-ACCESS read-write
                STATUS current
                DESCRIPTION
					"If your WAN connection type is PPTP or L2TP, Please enter the server name or server ip of the 
					VPN server."
                ::= { qRPPTPL2TP 9 }
				
-- -------------------------------------------------------------------------
-- *  End of qRouterMode - PPTP and L2TP Setting Section
-- -------------------------------------------------------------------------  

-- -------------------------------------------------------------------------
-- *  qRouterMode - Special Requirement from ISP Setting Section
-- -------------------------------------------------------------------------
						
	qRSpecialRequirementFromISP	OBJECT IDENTIFIER ::={ qRInternetSetup 6 }
	
	qRSelectISPProfile	OBJECT-TYPE
				SYNTAX INTEGER { none(1), unifi-home(2), unifi-business(3), singtel-mio(4), singtel-others(5), m1-fiber(6), maxis-fiber(7), maxis-fiber-special(8), manual(9) }
				MAX-ACCESS read-write
				STATUS current
				DESCRIPTION ""
				::= { qRSpecialRequirementFromISP 1 }

	qRIptvSTBPort	OBJECT-TYPE
				SYNTAX OCTET STRING
				MAX-ACCESS read-only
				STATUS current
				DESCRIPTION 
					"Show the IPTV STB Port."
				::= { qRSpecialRequirementFromISP 2 }

	qRVoipPort	OBJECT-TYPE
                SYNTAX OCTET STRING
                MAX-ACCESS read-only
                STATUS current
                DESCRIPTION 
                	"Show the VoIP Port."
                ::= { qRSpecialRequirementFromISP 3 }
	
	qRInternetVID	OBJECT-TYPE
				SYNTAX OCTET STRING
				MAX-ACCESS read-write
				STATUS current
				DESCRIPTION 
					"User can set this variable only when 'selectISPProfile' is 'manual'. 
					 Blank value means internetVID won't be used. Value Range: 2-4094."
				::= { qRSpecialRequirementFromISP 4 }

	qRInternetPRIO	OBJECT-TYPE
				SYNTAX INTEGER ( 0..7 )
				MAX-ACCESS read-write
				STATUS current
				DESCRIPTION 
					"User can set this variable only when 'selectISPProfile' is 'manual'. "
				::= { qRSpecialRequirementFromISP 5 }

	qRLan4PortVID	OBJECT-TYPE
				SYNTAX OCTET STRING
				MAX-ACCESS read-write
				STATUS current
				DESCRIPTION 
					"User can set this variable only when 'selectISPProfil'e is 'manual'. 
					Blank value means internetVID won't be used. Value Range: 2-4094."
				::= { qRSpecialRequirementFromISP 6 }

	qRLan4PortPRIO	OBJECT-TYPE
				SYNTAX INTEGER ( 0..7 )
				MAX-ACCESS read-write
				STATUS current
				DESCRIPTION 
					"User can set this variable only when 'selectISPProfile' is 'manual'. "
				::= { qRSpecialRequirementFromISP 7 }
				
	qRLan3PortVID	OBJECT-TYPE
				SYNTAX OCTET STRING
				MAX-ACCESS read-write
				STATUS current
				DESCRIPTION 
					"User can set this variable only when 'selectISPProfile' is 'manual'. 
					Blank value means internetVID won't be used. Value Range: 2-4094."
				::= { qRSpecialRequirementFromISP 8 }

	qRLan3PortPRIO	OBJECT-TYPE
				SYNTAX INTEGER ( 0..7 )
				MAX-ACCESS read-write
				STATUS current
				DESCRIPTION 
					"User can set this variable only when 'selectISPProfile' is 'manual'. "
				::= { qRSpecialRequirementFromISP 9 }

-- ----------------------------------------------------------------------
-- *  End of qRouterMode - Special Requirement from ISP Setting Section
-- ----------------------------------------------------------------------
-- ++++++++++++++++++++++++++++++++++++++++++++++++++++++++++++++++++++++
-- *  End of Internet Setup Section 
-- ++++++++++++++++++++++++++++++++++++++++++++++++++++++++++++++++++++++

-- ++++++++++++++++++++++++++++++++++++++++++++++++++++++++++++++++++++++
-- *  qRouterMode - Wireless Setting Section
-- ++++++++++++++++++++++++++++++++++++++++++++++++++++++++++++++++++++++
	
	qRWirelessSetting	OBJECT IDENTIFIER ::= { qRouterMode 2 }
                                                                            
	qRnetworkNameWl2g	OBJECT-TYPE
                SYNTAX OCTET STRING
                MAX-ACCESS read-write
				STATUS current
                DESCRIPTION ""
				::= { qRWirelessSetting 1 }

	qRnetworkKeyWl2g	OBJECT-TYPE
                SYNTAX OCTET STRING
                MAX-ACCESS read-write
                STATUS current
				DESCRIPTION ""
				::= { qRWirelessSetting 2 }

	qRnetworkNameWl5g	OBJECT-TYPE
                SYNTAX OCTET STRING
                MAX-ACCESS read-write
				STATUS current
                DESCRIPTION ""
				::= { qRWirelessSetting 3 }

	qRnetworkKeyWl5g	OBJECT-TYPE
                SYNTAX OCTET STRING
                MAX-ACCESS read-write
                STATUS current
				DESCRIPTION ""
				::= { qRWirelessSetting 4 }
-- ++++++++++++++++++++++++++++++++++++++++++++++++++++++++++++++++++++++
-- *  End of qRouterMode - Wireless Setting Section
-- ++++++++++++++++++++++++++++++++++++++++++++++++++++++++++++++++++++++                                                                                                                                                        
-- **********************************************************************
-- *  End of qRouterMode Setting Section
-- **********************************************************************
                                                                          

-- **********************************************************************
-- *  Repeater Mode Section
-- **********************************************************************

	qRepeaterMode	OBJECT IDENTIFIER ::= { quickInternetSetup 2 }
	
	qAPScanAct	OBJECT-TYPE
				SYNTAX INTEGER { scan(1), nothing(2) }
				MAX-ACCESS read-write
				STATUS current
				DESCRIPTION ""
				::= { qRepeaterMode 1 }

	qAPScanTable	OBJECT-TYPE
				SYNTAX SEQUENCE OF QAPScanEntry
				MAX-ACCESS not-accessible
				STATUS current
				DESCRIPTION ""
                ::= { qRepeaterMode 2 }

	qAPScanEntry	OBJECT-TYPE
				SYNTAX QAPScanEntry
				MAX-ACCESS not-accessible
				STATUS current
				DESCRIPTION ""
				INDEX { qAPResultIndex }
				::= { qAPScanTable 1 }

 	QAPScanEntry ::= SEQUENCE {
        qAPResultIndex 		INTEGER,
		qAPResultBand	    OCTET STRING,
        qAPResultSSID		OCTET STRING,
		qAPResultChannel	INTEGER,
		qAPResultAuthentication	INTEGER,
		qAPResultEncryption	INTEGER,
		qAPResultRssi		INTEGER,
		qAPResultBSSID	    OCTET STRING,
		qAPResultMode		INTEGER,
		qAPResultStatus		INTEGER
    	}

	qAPResultIndex	OBJECT-TYPE
				SYNTAX INTEGER ( 1..32 )
				MAX-ACCESS not-accessible
				STATUS current
				DESCRIPTION
					"AP scan result entry index."
				::= { qAPScanEntry 1 }

	qAPResultBand	OBJECT-TYPE
				SYNTAX OCTET STRING
				MAX-ACCESS read-only
				STATUS current
				DESCRIPTION
					"Band of the AP scan result."
				::= { qAPScanEntry 2 }

	qAPResultSSID		OBJECT-TYPE
				SYNTAX OCTET STRING ( SIZE (1..32) )
				MAX-ACCESS read-only
				STATUS current
				DESCRIPTION
					"SSID of the AP scan result."
				::= { qAPScanEntry 3 }

	qAPResultChannel	OBJECT-TYPE
				SYNTAX INTEGER
				MAX-ACCESS read-only
				STATUS current
				DESCRIPTION
					"Channel of the AP scan result."
				::= { qAPScanEntry 4 }


	qAPResultAuthentication	OBJECT-TYPE
				SYNTAX INTEGER { open-system(1), wpa-enterprise(2), wpa2-enterprise(3), wpa-personl(4), wpa2-personl(5), none(6), radius-with-8021x(7), unknown(8) }
				MAX-ACCESS read-only
				STATUS current
				DESCRIPTION
					"Authentication of the AP scan result."
				::= { qAPScanEntry 5 }

	qAPResultEncryption	OBJECT-TYPE
				SYNTAX INTEGER { none(1), wep(2), tkip(3), aes(4), tkip-aes(5), unknown(6) }
				MAX-ACCESS read-only
				STATUS current
				DESCRIPTION
					"Encryption of the AP scan result."
				::= { qAPScanEntry 6 }

	qAPResultRssi		OBJECT-TYPE
				SYNTAX INTEGER
				MAX-ACCESS read-only
				STATUS current
				DESCRIPTION
					"Rssi of the AP scan result."
				::= { qAPScanEntry 7 }

	qAPResultBSSID		OBJECT-TYPE
				SYNTAX OCTET STRING
				MAX-ACCESS read-only
				STATUS current
				DESCRIPTION
					"BSSID of the AP scan result."
				::= { qAPScanEntry 8 }

	qAPResultMode		OBJECT-TYPE
				SYNTAX INTEGER { a(1), b(2), an(3), bg(4), bgn(5) }
				MAX-ACCESS read-only
				STATUS current
				DESCRIPTION
					"Mode of the AP scan result."
				::= { qAPScanEntry 9 }

	qAPResultStatus		OBJECT-TYPE
				SYNTAX INTEGER
				MAX-ACCESS read-only
				STATUS current
				DESCRIPTION
					"Status of the AP scan result."
				::= { qAPScanEntry 10 }
                                                                  
	qWlcBand	OBJECT-TYPE
				SYNTAX INTEGER { band2g(1), band5g(2) }
				MAX-ACCESS read-write
				STATUS current
				DESCRIPTION ""
				::= { qRepeaterMode 3 }

	qWlcSsid	OBJECT-TYPE
				SYNTAX OCTET STRING ( SIZE (1..32) )
				MAX-ACCESS read-write
				STATUS current
				DESCRIPTION 
					"The network name that RT-AC66U will connect to."
				::= { qRepeaterMode 4 }

	qWlcAuthentication	OBJECT-TYPE                              
                SYNTAX INTEGER { open-system(1), shared-key(2), wpa-personal(3), wpa2-personal(4), wpa-enterprise(5), wpa2-enterprise(6), radius-with-8021x(7) }
				MAX-ACCESS read-write
				STATUS current
				DESCRIPTION ""
				::= { qRepeaterMode 5 }

	qWlcWepEncryption	OBJECT-TYPE
				SYNTAX INTEGER { none(1), wep-64bits(2), wep-128bits(3) }
				MAX-ACCESS read-write
				STATUS current
				DESCRIPTION ""
				::= { qRepeaterMode 6 }

	qWlcKeyIndex	OBJECT-TYPE
				SYNTAX INTEGER { first(1), second(2), third(3), forth(4) }
				MAX-ACCESS read-write                      
                STATUS current
				DESCRIPTION ""
				::= { qRepeaterMode 7 }

	qWlcWepKeyValue	OBJECT-TYPE
				SYNTAX OCTET STRING
				MAX-ACCESS read-write
 				STATUS current
 				DESCRIPTION ""
				::= { qRepeaterMode  8 }

	qWlcWpaEncryption	OBJECT-TYPE
				SYNTAX INTEGER { tkip(1), aes(2), tkip-aes(3), none(0) }
				MAX-ACCESS read-write
				STATUS current
				DESCRIPTION ""
 				::= { qRepeaterMode 9 }

	qWlcWpaPreSharedKey	OBJECT-TYPE
               	SYNTAX OCTET STRING
              	MAX-ACCESS read-write
               	STATUS current
			   	DESCRIPTION ""
				::= { qRepeaterMode 10 }
                                               	
	qTWirelessSetting	OBJECT IDENTIFIER ::= { qRepeaterMode 11 }   
	
	qTUseDefaultSettings	OBJECT-TYPE
				SYNTAX INTEGER { yes(1), nothing(2) }
				MAX-ACCESS read-write
				STATUS current
				DESCRIPTION 
					"Select 'yes' to use the same settings as the network you want to extend."
                ::= { qTWirelessSetting 1 }	
                                                                            
	qTnetworkNameWl2g	OBJECT-TYPE
                SYNTAX OCTET STRING
                MAX-ACCESS read-write
				STATUS current
                DESCRIPTION 
                	"The Network name of RT-AC66U 2.4G band."
				::= { qTWirelessSetting 2 }

	qTnetworkKeyWl2g	OBJECT-TYPE
                SYNTAX OCTET STRING
                MAX-ACCESS read-write
                STATUS current
				DESCRIPTION 
					"The Network key of RT-AC66U 2.4G band."
				::= { qTWirelessSetting 3 }

	qTnetworkNameWl5g	OBJECT-TYPE
                SYNTAX OCTET STRING
                MAX-ACCESS read-write
				STATUS current
                DESCRIPTION 
                	"The Network key of RT-AC66U 5G band."
				::= { qTWirelessSetting 4 }

	qTnetworkKeyWl5g	OBJECT-TYPE
                SYNTAX OCTET STRING
                MAX-ACCESS read-write
                STATUS current
				DESCRIPTION 
					"The Network key of RT-AC66U 5G band."
				::= { qTWirelessSetting 5 }                                               
-- **********************************************************************
-- *  End of Repeater Mode Section
-- **********************************************************************
  
-- **********************************************************************
-- *  AP Mode Section
-- **********************************************************************            

	qApMode	OBJECT IDENTIFIER ::= { quickInternetSetup 3 }

-- ++++++++++++++++++++++++++++++++++++++++++++++++++++++++++++++++++++++
-- *  qApMode - Lan IP Setting Section
-- ++++++++++++++++++++++++++++++++++++++++++++++++++++++++++++++++++++++
                                                                       
	qlanIpSetting		OBJECT IDENTIFIER ::= { qApMode 1 }

	qlanGetIpAutomatically	OBJECT-TYPE
				SYNTAX INTEGER { yes(1), no(2) }
				MAX-ACCESS read-write
				STATUS current
				DESCRIPTION ""
                ::= { qlanIpSetting 1 }
	
	qlanIPAddress	OBJECT-TYPE
				SYNTAX IpAddress
				MAX-ACCESS read-write
				STATUS current
				DESCRIPTION
		           "The value of this object is IP Address of the device which is seen on your local network. 
					The default value is 192.168.1.1."
                ::= { qlanIpSetting 2 }

	qlanSubnetMask	OBJECT-TYPE
				SYNTAX IpAddress
				MAX-ACCESS read-write
				STATUS current
				DESCRIPTION
					"The value this object is Subnet Mask of the device which is seen on your local network. 
					The default value is 255.255.255.0."
				::= { qlanIpSetting 3 }

	qlanDefaultGateway		OBJECT-TYPE
				SYNTAX IpAddress
				MAX-ACCESS read-write
				STATUS current
				DESCRIPTION ""
				::= { qlanIpSetting 4 }

	qlanConnectToDnsServerAutomatically	OBJECT-TYPE
				SYNTAX INTEGER { yes(1), no(2) }
				MAX-ACCESS read-write
				STATUS current
				DESCRIPTION ""
                ::= { qlanIpSetting 5 }

	qlanDnsServer1	OBJECT-TYPE
				SYNTAX OCTET STRING ( SIZE (0..15) )
				MAX-ACCESS read-write
				STATUS current
				DESCRIPTION ""
				::= { qlanIpSetting 6 }

	qlanDnsServer2	OBJECT-TYPE
				SYNTAX OCTET STRING ( SIZE (0..15) )
				MAX-ACCESS read-write
				STATUS current
				DESCRIPTION ""
				::= { qlanIpSetting 7 }

-- ++++++++++++++++++++++++++++++++++++++++++++++++++++++++++++++++++++++
-- *  End of qApMode - Lan IP Setting Section
-- ++++++++++++++++++++++++++++++++++++++++++++++++++++++++++++++++++++++   
-- ++++++++++++++++++++++++++++++++++++++++++++++++++++++++++++++++++++++
-- *  qApMode - Wireless Setting Section
-- ++++++++++++++++++++++++++++++++++++++++++++++++++++++++++++++++++++++
	
	qPWirelessSetting	OBJECT IDENTIFIER ::= { qApMode 2 }
                                                                            
	qPnetworkNameWl2g	OBJECT-TYPE
                SYNTAX OCTET STRING
                MAX-ACCESS read-write
				STATUS current
                DESCRIPTION ""
				::= { qPWirelessSetting 1 }

	qPnetworkKeyWl2g	OBJECT-TYPE
                SYNTAX OCTET STRING
                MAX-ACCESS read-write
                STATUS current
				DESCRIPTION ""
				::= { qPWirelessSetting 2 }

	qPnetworkNameWl5g	OBJECT-TYPE
                SYNTAX OCTET STRING
                MAX-ACCESS read-write
				STATUS current
                DESCRIPTION ""
				::= { qPWirelessSetting 3 }

	qPnetworkKeyWl5g	OBJECT-TYPE
                SYNTAX OCTET STRING
                MAX-ACCESS read-write
                STATUS current
				DESCRIPTION ""
				::= { qPWirelessSetting 4 }
-- ++++++++++++++++++++++++++++++++++++++++++++++++++++++++++++++++++++++
-- *  End of qApMode - Wireless Setting Section
-- ++++++++++++++++++++++++++++++++++++++++++++++++++++++++++++++++++++++ 

-- **********************************************************************
-- *  End of AP Mode Section
-- **********************************************************************
 
-- **********************************************************************
-- *  Media Bridge Mode Section
-- **********************************************************************   

	qMediaBridgeMode	OBJECT IDENTIFIER ::= { quickInternetSetup 4 }
	
	qmAPScanAct	OBJECT-TYPE
				SYNTAX INTEGER { scan(1), nothing(2) }
				MAX-ACCESS read-write
				STATUS current
				DESCRIPTION ""
				::= { qMediaBridgeMode 1 }

	qmAPScanTable	OBJECT-TYPE
				SYNTAX SEQUENCE OF QmAPScanEntry
				MAX-ACCESS not-accessible
				STATUS current
				DESCRIPTION ""
                ::= { qMediaBridgeMode 2 }

	qmAPScanEntry	OBJECT-TYPE
				SYNTAX QmAPScanEntry
				MAX-ACCESS not-accessible
				STATUS current
				DESCRIPTION ""
				INDEX { qmAPResultIndex }
				::= { qmAPScanTable 1 }

 	QmAPScanEntry ::= SEQUENCE {
        qmAPResultIndex 			INTEGER,
		qmAPResultBand	    		OCTET STRING,
        qmAPResultSSID				OCTET STRING,
		qmAPResultChannel			INTEGER,
		qmAPResultAuthentication	INTEGER,
		qmAPResultEncryption		INTEGER,
		qmAPResultRssi				INTEGER,
		qmAPResultBSSID	    		OCTET STRING,
		qmAPResultMode				INTEGER,
		qmAPResultStatus			INTEGER
    	}

	qmAPResultIndex	OBJECT-TYPE
				SYNTAX INTEGER ( 1..32 )
				MAX-ACCESS not-accessible
				STATUS current
				DESCRIPTION
					"AP scan result entry index."
				::= { qmAPScanEntry 1 }

	qmAPResultBand	OBJECT-TYPE
				SYNTAX OCTET STRING
				MAX-ACCESS read-only
				STATUS current
				DESCRIPTION
					"Band of the AP scan result."
				::= { qmAPScanEntry 2 }

	qmAPResultSSID		OBJECT-TYPE
				SYNTAX OCTET STRING ( SIZE (1..32) )
				MAX-ACCESS read-only
				STATUS current
				DESCRIPTION
					"SSID of the AP scan result."
				::= { qmAPScanEntry 3 }

	qmAPResultChannel	OBJECT-TYPE
				SYNTAX INTEGER
				MAX-ACCESS read-only
				STATUS current
				DESCRIPTION
					"Channel of the AP scan result."
				::= { qmAPScanEntry 4 }


	qmAPResultAuthentication	OBJECT-TYPE
				SYNTAX INTEGER { open-system(1), wpa-enterprise(2), wpa2-enterprise(3), wpa-personl(4), wpa2-personl(5), none(6), radius-with-8021x(7), unknown(8) }
				MAX-ACCESS read-only
				STATUS current
				DESCRIPTION
					"Authentication of the AP scan result."
				::= { qmAPScanEntry 5 }

	qmAPResultEncryption	OBJECT-TYPE
				SYNTAX INTEGER { none(1), wep(2), tkip(3), aes(4), tkip-aes(5), unknown(6) }
				MAX-ACCESS read-only
				STATUS current
				DESCRIPTION
					"Encryption of the AP scan result."
				::= { qmAPScanEntry 6 }

	qmAPResultRssi		OBJECT-TYPE
				SYNTAX INTEGER
				MAX-ACCESS read-only
				STATUS current
				DESCRIPTION
					"Rssi of the AP scan result."
				::= { qmAPScanEntry 7 }

	qmAPResultBSSID		OBJECT-TYPE
				SYNTAX OCTET STRING
				MAX-ACCESS read-only
				STATUS current
				DESCRIPTION
					"BSSID of the AP scan result."
				::= { qmAPScanEntry 8 }

	qmAPResultMode		OBJECT-TYPE
				SYNTAX INTEGER { a(1), b(2), an(3), bg(4), bgn(5) }
				MAX-ACCESS read-only
				STATUS current
				DESCRIPTION
					"Mode of the AP scan result."
				::= { qmAPScanEntry 9 }

	qmAPResultStatus	OBJECT-TYPE
				SYNTAX INTEGER
				MAX-ACCESS read-only
				STATUS current
				DESCRIPTION
					"Status of the AP scan result."
				::= { qmAPScanEntry 10 }
                                                                  
	qmWlcBand	OBJECT-TYPE
				SYNTAX INTEGER { band2g(1), band5g(2) }
				MAX-ACCESS read-write
				STATUS current
				DESCRIPTION ""
				::= { qMediaBridgeMode 3 }

	qmWlcSsid	OBJECT-TYPE
				SYNTAX OCTET STRING ( SIZE (1..32) )
				MAX-ACCESS read-write
				STATUS current
				DESCRIPTION 
					"The network name that RT-AC66U will connect to."
				::= { qMediaBridgeMode 4 }

	qmWlcAuthentication	OBJECT-TYPE                              
                SYNTAX INTEGER { open-system(1), shared-key(2), wpa-personal(3), wpa2-personal(4), wpa-enterprise(5), wpa2-enterprise(6), radius-with-8021x(7) }
				MAX-ACCESS read-write
				STATUS current
				DESCRIPTION ""
				::= { qMediaBridgeMode 5 }

	qmWlcWepEncryption	OBJECT-TYPE
				SYNTAX INTEGER { none(1), wep-64bits(2), wep-128bits(3) }
				MAX-ACCESS read-write
				STATUS current
				DESCRIPTION ""
				::= { qMediaBridgeMode 6 }

	qmWlcKeyIndex	OBJECT-TYPE
				SYNTAX INTEGER { first(1), second(2), third(3), forth(4) }
				MAX-ACCESS read-write                      
                STATUS current
				DESCRIPTION ""
				::= { qMediaBridgeMode 7 }

	qmWlcWepKeyValue	OBJECT-TYPE
				SYNTAX OCTET STRING
				MAX-ACCESS read-write
 				STATUS current
 				DESCRIPTION ""
				::= { qMediaBridgeMode  8 }

	qmWlcWpaEncryption	OBJECT-TYPE
				SYNTAX INTEGER { tkip(1), aes(2), tkip-aes(3), none(0) }
				MAX-ACCESS read-write
				STATUS current
				DESCRIPTION ""
 				::= { qMediaBridgeMode 9 }

	qmWlcWpaPreSharedKey	OBJECT-TYPE
               	SYNTAX OCTET STRING
              	MAX-ACCESS read-write
               	STATUS current
			   	DESCRIPTION ""
				::= { qMediaBridgeMode 10 }                                                        	

-- **********************************************************************
-- *  End of Media Bridge Mode Section
-- **********************************************************************

  
-- ======================================================================
-- * End of Quick Internet Setup Section
-- ======================================================================

END
