-- $Id: pkcs10.asn1,v 1.1.1.1 2011/06/10 09:34:42 andrew Exp $
PKCS10 DEFINITIONS ::=

BEGIN

IMPORTS
	Name, SubjectPublicKeyInfo, Attribute, AlgorithmIdentifier
	FROM rfc2459;


CertificationRequestInfo ::= SEQUENCE {
    version       INTEGER { pkcs10-v1(0) },
    subject       Name,
    subjectPKInfo SubjectPublicKeyInfo,
    attributes    [0] IMPLICIT SET OF Attribute OPTIONAL 
}

CertificationRequest ::= SEQUENCE {
    certificationRequestInfo CertificationRequestInfo,
    signatureAlgorithm	     AlgorithmIdentifier,
    signature                BIT STRING
}

END
